--
-- SUMA-AAA-MIB.mib
-- MIB generated by MG-SOFT Visual MIB Builder Version 4.0 Build 349
-- Tuesday, March 18, 2014 at 14:13:31
--

	SUMA-AAA-MIB DEFINITIONS ::= BEGIN
 
		IMPORTS
			TimeTicks, IpAddress, Unsigned32, Counter64, 
			OBJECT-TYPE, OBJECT-IDENTITY			
				FROM SNMPv2-SMI
			topvisionEponTree
				FROM SUMA-EPONEOC-EPON-MIB			
			RowStatus, TimeStamp, DisplayString, MacAddress, TEXTUAL-CONVENTION, DateAndTime	
				FROM SNMPv2-TC  
			InetAddressIPv6,InetAddressType,InetAddress
        		FROM INET-ADDRESS-MIB;

	                                
	                             
	
--
-- Textual conventions
--
		
--
-- Node definitions
--
			
		-- 1.3.6.1.4.1.32285.11.2.3.13
		topAAA OBJECT IDENTIFIER ::= { topvisionEponTree 13 }

		
		-- 1.3.6.1.4.1.32285.11.2.3.13.1
		topAAAConfigObjects OBJECT IDENTIFIER ::= { topAAA 1 }

		
		-- 1.3.6.1.4.1.32285.11.2.3.13.1.1
		topAAAGroupTable OBJECT-TYPE
			SYNTAX SEQUENCE OF TopAAAGroupEntry
			MAX-ACCESS not-accessible
			STATUS current
			DESCRIPTION
				"AAA group talbe."
			::= { topAAAConfigObjects 1 }

		
		-- 1.3.6.1.4.1.32285.11.2.3.13.1.1.1
		topAAAGroupEntry OBJECT-TYPE
			SYNTAX TopAAAGroupEntry
			MAX-ACCESS not-accessible
			STATUS current
			DESCRIPTION
				"AAA group entry."
			INDEX { topAAAGroupIndex }
			::= { topAAAGroupTable 1 }

		
		TopAAAGroupEntry ::=
			SEQUENCE { 
				topAAAGroupIndex
					INTEGER,
				topAAAGroupName
					OCTET STRING,
				topAAAGroupPrivilege
					INTEGER,
				topAAAGroupRowStatus
					RowStatus
			 }

		-- 1.3.6.1.4.1.32285.11.2.3.13.1.1.1.1
		topAAAGroupIndex OBJECT-TYPE
			SYNTAX INTEGER (1..5)
			MAX-ACCESS not-accessible
			STATUS current
			DESCRIPTION
				"AAA group index."
			::= { topAAAGroupEntry 1 }

		
		-- 1.3.6.1.4.1.32285.11.2.3.13.1.1.1.2
		topAAAGroupName OBJECT-TYPE
			SYNTAX OCTET STRING (SIZE (1..50))
			MAX-ACCESS read-create
			STATUS current
			DESCRIPTION
				"AAA group name."
			::= { topAAAGroupEntry 2 }

		
		-- 1.3.6.1.4.1.32285.11.2.3.13.1.1.1.3
		topAAAGroupPrivilege OBJECT-TYPE
			SYNTAX INTEGER (0..15)
			MAX-ACCESS read-write
			STATUS current
			DESCRIPTION
				"AAA group privilege."
			::= { topAAAGroupEntry 3 }

		
		-- 1.3.6.1.4.1.32285.11.2.3.13.1.1.1.4
		topAAAGroupRowStatus OBJECT-TYPE
			SYNTAX RowStatus
			MAX-ACCESS read-create
			STATUS current
			DESCRIPTION
				"Row Status. This object indicates the row status of this table:
				createAndGo(4): indicates that a row is created.
				destroy(6): indicates that a row is deleted."
			::= { topAAAGroupEntry 4 }

		
		-- 1.3.6.1.4.1.32285.11.2.3.13.1.2
		topAAAUserTable OBJECT-TYPE
			SYNTAX SEQUENCE OF TopAAAUserEntry
			MAX-ACCESS not-accessible
			STATUS current
			DESCRIPTION
				"AAA user table."
			::= { topAAAConfigObjects 2 }

		
		-- 1.3.6.1.4.1.32285.11.2.3.13.1.2.1
		topAAAUserEntry OBJECT-TYPE
			SYNTAX TopAAAUserEntry
			MAX-ACCESS not-accessible
			STATUS current
			DESCRIPTION
				"AAA user entry."
			INDEX { topAAAUserIndex }
			::= { topAAAUserTable 1 }

		
		TopAAAUserEntry ::=
			SEQUENCE { 
				topAAAUserIndex
					INTEGER,
				topAAAUserName
					OCTET STRING,
				topAAAUserGroupName
					OCTET STRING,
				topAAAUserPwd
					OCTET STRING,
				topAAAUserRowStatus
					RowStatus
			 }

		-- 1.3.6.1.4.1.32285.11.2.3.13.1.2.1.1
		topAAAUserIndex OBJECT-TYPE
			SYNTAX INTEGER (1..50)
			MAX-ACCESS not-accessible
			STATUS current
			DESCRIPTION
				"AAA user index."
			::= { topAAAUserEntry 1 }

		
		-- 1.3.6.1.4.1.32285.11.2.3.13.1.2.1.2
		topAAAUserName OBJECT-TYPE
			SYNTAX OCTET STRING (SIZE (1..50))
			MAX-ACCESS read-create
			STATUS current
			DESCRIPTION
				"AAA user name."
			::= { topAAAUserEntry 2 }

		
		-- 1.3.6.1.4.1.32285.11.2.3.13.1.2.1.3
		topAAAUserGroupName OBJECT-TYPE
			SYNTAX OCTET STRING (SIZE (1..50))
			MAX-ACCESS read-write
			STATUS current
			DESCRIPTION
				"The name of AAA user belongs to group."
			::= { topAAAUserEntry 3 }

		
		-- 1.3.6.1.4.1.32285.11.2.3.13.1.2.1.4
		topAAAUserPwd OBJECT-TYPE
			SYNTAX OCTET STRING (SIZE (1..50))
			MAX-ACCESS read-write
			STATUS current
			DESCRIPTION
				"AAA user password."
			::= { topAAAUserEntry 4 }

		
		-- 1.3.6.1.4.1.32285.11.2.3.13.1.2.1.5
		topAAAUserRowStatus OBJECT-TYPE
			SYNTAX RowStatus
			MAX-ACCESS read-create
			STATUS current
			DESCRIPTION
				"Row Status. This object indicates the row status of this table:
				createAndGo(4): indicates that a row is created.
				destroy(6): indicates that a row is deleted."
			::= { topAAAUserEntry 5 }

		
		-- 1.3.6.1.4.1.32285.11.2.3.13.1.3
		topAAASettingObjects OBJECT IDENTIFIER ::= { topAAAConfigObjects 3 }

		
		-- 1.3.6.1.4.1.32285.11.2.3.13.1.3.1
		topAAAIsActive OBJECT-TYPE
			SYNTAX INTEGER
				{
				enable(1),
				disable(2)
				}
			MAX-ACCESS read-write
			STATUS current
			DESCRIPTION
				"Whether AAA is active."
			::= { topAAASettingObjects 1 }

		
		-- 1.3.6.1.4.1.32285.11.2.3.13.1.3.2
		topAAALocalOverride OBJECT-TYPE
			SYNTAX INTEGER
				{
				enable(1),
				disable(2)
				}
			MAX-ACCESS read-write
			STATUS current
			DESCRIPTION
				"Whether AAA Local Override is active."
			::= { topAAASettingObjects 2 }

		
		-- 1.3.6.1.4.1.32285.11.2.3.13.1.4
		topAAALoginAuthenTable OBJECT-TYPE
			SYNTAX SEQUENCE OF TopAAALoginAuthenEntry
			MAX-ACCESS not-accessible
			STATUS current
			DESCRIPTION
				"AAA login authentication method table."
			::= { topAAAConfigObjects 4 }

		
		-- 1.3.6.1.4.1.32285.11.2.3.13.1.4.1
		topAAALoginAuthenEntry OBJECT-TYPE
			SYNTAX TopAAALoginAuthenEntry
			MAX-ACCESS not-accessible
			STATUS current
			DESCRIPTION
				"AAA login authentication method entry."
			INDEX { topAAALoginGrpNameIndex }
			::= { topAAALoginAuthenTable 1 }

		
		TopAAALoginAuthenEntry ::=
			SEQUENCE { 
				topAAALoginGrpNameIndex
					OCTET STRING,
				topAAALoginModList
					OCTET STRING
			 }

		-- 1.3.6.1.4.1.32285.11.2.3.13.1.4.1.1
		topAAALoginGrpNameIndex OBJECT-TYPE
			SYNTAX OCTET STRING (SIZE (1..51))
			MAX-ACCESS not-accessible
			STATUS current
			DESCRIPTION
				"AAA group name."
			::= { topAAALoginAuthenEntry 1 }

		
		-- 1.3.6.1.4.1.32285.11.2.3.13.1.4.1.2
		topAAALoginModList OBJECT-TYPE
			SYNTAX OCTET STRING (SIZE (5))
			MAX-ACCESS read-write
			STATUS current
			DESCRIPTION
				"The list of AAA login authentication method."
			::= { topAAALoginAuthenEntry 2 }

		
		-- 1.3.6.1.4.1.32285.11.2.3.13.1.5
		topAAAEnableAuthenTable OBJECT-TYPE
			SYNTAX SEQUENCE OF TopAAAEnableAuthenEntry
			MAX-ACCESS not-accessible
			STATUS current
			DESCRIPTION
				"AAA enable authentication method table."
			::= { topAAAConfigObjects 5 }

		
		-- 1.3.6.1.4.1.32285.11.2.3.13.1.5.1
		topAAAEnableAuthenEntry OBJECT-TYPE
			SYNTAX TopAAAEnableAuthenEntry
			MAX-ACCESS not-accessible
			STATUS current
			DESCRIPTION
				"AAA enable authentication method entry."
			INDEX { topAAAEnableGrpNameIndex }
			::= { topAAAEnableAuthenTable 1 }

		
		TopAAAEnableAuthenEntry ::=
			SEQUENCE { 
				topAAAEnableGrpNameIndex
					OCTET STRING,
				topAAAEnableModList
					OCTET STRING
			 }

		-- 1.3.6.1.4.1.32285.11.2.3.13.1.5.1.1
		topAAAEnableGrpNameIndex OBJECT-TYPE
			SYNTAX OCTET STRING (SIZE (1..51))
			MAX-ACCESS not-accessible
			STATUS current
			DESCRIPTION
				"AAA group name."
			::= { topAAAEnableAuthenEntry 1 }

		
		-- 1.3.6.1.4.1.32285.11.2.3.13.1.5.1.2
		topAAAEnableModList OBJECT-TYPE
			SYNTAX OCTET STRING (SIZE (5))
			MAX-ACCESS read-write
			STATUS current
			DESCRIPTION
				"The list of AAA enable authentication method."
			::= { topAAAEnableAuthenEntry 2 }

		
		-- 1.3.6.1.4.1.32285.11.2.3.13.1.6
		topAAACmdAuthorTable OBJECT-TYPE
			SYNTAX SEQUENCE OF TopAAACmdAuthorEntry
			MAX-ACCESS not-accessible
			STATUS current
			DESCRIPTION
				"AAA command authorization method table."
			::= { topAAAConfigObjects 6 }

		
		-- 1.3.6.1.4.1.32285.11.2.3.13.1.6.1
		topAAACmdAuthorEntry OBJECT-TYPE
			SYNTAX TopAAACmdAuthorEntry
			MAX-ACCESS not-accessible
			STATUS current
			DESCRIPTION
				"AAA command authorization method entry."
			INDEX { topAAACmdLevelIndex, topAAACmdGrpNameIndex }
			::= { topAAACmdAuthorTable 1 }

		
		TopAAACmdAuthorEntry ::=
			SEQUENCE { 
				topAAACmdLevelIndex
					INTEGER,
				topAAACmdGrpNameIndex
					OCTET STRING,
				topAAACmdModList
					OCTET STRING,
				topAAACmdRowStatus
					RowStatus
			 }

		-- 1.3.6.1.4.1.32285.11.2.3.13.1.6.1.1
		topAAACmdLevelIndex OBJECT-TYPE
			SYNTAX INTEGER (0..15)
			MAX-ACCESS not-accessible
			STATUS current
			DESCRIPTION
				"AAA user level."
			::= { topAAACmdAuthorEntry 1 }

		
		-- 1.3.6.1.4.1.32285.11.2.3.13.1.6.1.2
		topAAACmdGrpNameIndex OBJECT-TYPE
			SYNTAX OCTET STRING (SIZE (1..51))
			MAX-ACCESS not-accessible
			STATUS current
			DESCRIPTION
				"AAA group name."
			::= { topAAACmdAuthorEntry 2 }

		
		-- 1.3.6.1.4.1.32285.11.2.3.13.1.6.1.3
		topAAACmdModList OBJECT-TYPE
			SYNTAX OCTET STRING (SIZE (5))
			MAX-ACCESS read-write
			STATUS current
			DESCRIPTION
				"The list of AAA command authorization method."
			::= { topAAACmdAuthorEntry 3 }

		
		-- 1.3.6.1.4.1.32285.11.2.3.13.1.6.1.4
		topAAACmdRowStatus OBJECT-TYPE
			SYNTAX RowStatus
			MAX-ACCESS read-create
			STATUS current
			DESCRIPTION
				"Row Status. This object indicates the row status of this table:
				createAndGo(4): indicates that a row is created.
				destroy(6): indicates that a row is deleted."
			::= { topAAACmdAuthorEntry 4 }

		
		-- 1.3.6.1.4.1.32285.11.2.3.13.1.7
		topAAAExecAuthorTable OBJECT-TYPE
			SYNTAX SEQUENCE OF TopAAAExecAuthorEntry
			MAX-ACCESS not-accessible
			STATUS current
			DESCRIPTION
				"AAA login authorization method table."
			::= { topAAAConfigObjects 7 }

		
		-- 1.3.6.1.4.1.32285.11.2.3.13.1.7.1
		topAAAExecAuthorEntry OBJECT-TYPE
			SYNTAX TopAAAExecAuthorEntry
			MAX-ACCESS not-accessible
			STATUS current
			DESCRIPTION
				"AAA login authorization method entry."
			INDEX { topAAAExecGrpNameIndex }
			::= { topAAAExecAuthorTable 1 }

		
		TopAAAExecAuthorEntry ::=
			SEQUENCE { 
				topAAAExecGrpNameIndex
					OCTET STRING,
				topAAAExecModList
					OCTET STRING
			 }

		-- 1.3.6.1.4.1.32285.11.2.3.13.1.7.1.1
		topAAAExecGrpNameIndex OBJECT-TYPE
			SYNTAX OCTET STRING (SIZE (1..51))
			MAX-ACCESS not-accessible
			STATUS current
			DESCRIPTION
				"AAA group name."
			::= { topAAAExecAuthorEntry 1 }

		
		-- 1.3.6.1.4.1.32285.11.2.3.13.1.7.1.2
		topAAAExecModList OBJECT-TYPE
			SYNTAX OCTET STRING (SIZE (5))
			MAX-ACCESS read-write
			STATUS current
			DESCRIPTION
				"The list of AAA login authorization method ."
			::= { topAAAExecAuthorEntry 2 }

		
		-- 1.3.6.1.4.1.32285.11.2.3.13.1.8
		topAAACmdLevelTable OBJECT-TYPE
			SYNTAX SEQUENCE OF TopAAACmdLevelEntry
			MAX-ACCESS not-accessible
			STATUS current
			DESCRIPTION
				"Configure AAA command privilege table."
			::= { topAAAConfigObjects 8 }

		
		-- 1.3.6.1.4.1.32285.11.2.3.13.1.8.1
		topAAACmdLevelEntry OBJECT-TYPE
			SYNTAX TopAAACmdLevelEntry
			MAX-ACCESS not-accessible
			STATUS current
			DESCRIPTION
				"Configure AAA command privilege entry."
			INDEX { topAAACmdIndex }
			::= { topAAACmdLevelTable 1 }

		
		TopAAACmdLevelEntry ::=
			SEQUENCE { 
				topAAACmdIndex
					INTEGER,
				topAAACmdString
					OCTET STRING,
				topAAACmdLevel
					INTEGER,
				topAAACmdLevelRowStatus
					RowStatus
			 }

		-- 1.3.6.1.4.1.32285.11.2.3.13.1.8.1.1
		topAAACmdIndex OBJECT-TYPE
			SYNTAX INTEGER (1..100)
			MAX-ACCESS not-accessible
			STATUS current
			DESCRIPTION
				"AAA command index."
			::= { topAAACmdLevelEntry 1 }

		
		-- 1.3.6.1.4.1.32285.11.2.3.13.1.8.1.2
		topAAACmdString OBJECT-TYPE
			SYNTAX OCTET STRING (SIZE (1..30))
			MAX-ACCESS read-create
			STATUS current
			DESCRIPTION
				"AAA command line."
			::= { topAAACmdLevelEntry 2 }

		
		-- 1.3.6.1.4.1.32285.11.2.3.13.1.8.1.3
		topAAACmdLevel OBJECT-TYPE
			SYNTAX INTEGER (0..15)
			MAX-ACCESS read-write
			STATUS current
			DESCRIPTION
				"AAA command privilege."
			::= { topAAACmdLevelEntry 3 }

		
		-- 1.3.6.1.4.1.32285.11.2.3.13.1.8.1.4
		topAAACmdLevelRowStatus OBJECT-TYPE
			SYNTAX RowStatus
			MAX-ACCESS read-create
			STATUS current
			DESCRIPTION
				"Row Status. This object indicates the row status of this table:
				createAndGo(4): indicates that a row is created.
				destroy(6): indicates that a row is deleted."
			::= { topAAACmdLevelEntry 4 }

		
		-- 1.3.6.1.4.1.32285.11.2.3.13.1.9
		topAAAServerTable OBJECT-TYPE
			SYNTAX SEQUENCE OF TopAAAServerEntry
			MAX-ACCESS not-accessible
			STATUS current
			DESCRIPTION
				"Configure AAA tacacs+ or radius server table."
			::= { topAAAConfigObjects 9 }

		
		-- 1.3.6.1.4.1.32285.11.2.3.13.1.9.1
		topAAAServerEntry OBJECT-TYPE
			SYNTAX TopAAAServerEntry
			MAX-ACCESS not-accessible
			STATUS current
			DESCRIPTION
				"Configure AAA tacacs+ or radius server entry."
			INDEX { topAAAProtTypeIndex, topAAAServerTypeIndex }
			::= { topAAAServerTable 1 }

		
		TopAAAServerEntry ::=
			SEQUENCE { 
				topAAAProtTypeIndex
					INTEGER,
				topAAAServerTypeIndex
					INTEGER,
				topAAAServerHostIp
					IpAddress,
				topAAAServerKey
					OCTET STRING,
				topAAAServerRetry
					INTEGER,
				topAAAServerPort
					INTEGER,
				topAAAServerTimeOut
					INTEGER,     
				topAAAServerHostIpv6
				InetAddressIPv6
					
			 }

		-- 1.3.6.1.4.1.32285.11.2.3.13.1.9.1.1
		topAAAProtTypeIndex OBJECT-TYPE
			SYNTAX INTEGER
				{
				tacacs(1),
				radius(2)
				}
			MAX-ACCESS not-accessible
			STATUS current
			DESCRIPTION
				"The type of AAA protocol server."
			::= { topAAAServerEntry 1 }

		
		-- 1.3.6.1.4.1.32285.11.2.3.13.1.9.1.2
		topAAAServerTypeIndex OBJECT-TYPE
			SYNTAX INTEGER
				{
				primary(1),
				secondary(2)
				}
			MAX-ACCESS not-accessible
			STATUS current
			DESCRIPTION
				"The configurator type of AAA tacacs+ or radius server."
			::= { topAAAServerEntry 2 }

		
		-- 1.3.6.1.4.1.32285.11.2.3.13.1.9.1.3
		topAAAServerHostIp OBJECT-TYPE
			SYNTAX IpAddress
			MAX-ACCESS read-write
			STATUS current
			DESCRIPTION
				"AAA server host IP address."
			::= { topAAAServerEntry 3 }

		
		-- 1.3.6.1.4.1.32285.11.2.3.13.1.9.1.4
		topAAAServerKey OBJECT-TYPE
			SYNTAX OCTET STRING (SIZE (0..32))
			MAX-ACCESS read-write
			STATUS current
			DESCRIPTION
				"AAA server key."
			::= { topAAAServerEntry 4 }

		
		-- 1.3.6.1.4.1.32285.11.2.3.13.1.9.1.5
		topAAAServerRetry OBJECT-TYPE
			SYNTAX INTEGER (0..5)
			MAX-ACCESS read-write
			STATUS current
			DESCRIPTION
				"The number of AAA server retry."
			DEFVAL { 1 }
			::= { topAAAServerEntry 5 }

		
		-- 1.3.6.1.4.1.32285.11.2.3.13.1.9.1.6
		topAAAServerPort OBJECT-TYPE
			SYNTAX INTEGER (1..65535)
			MAX-ACCESS read-write
			STATUS current
			DESCRIPTION
				"AAA server port."
			::= { topAAAServerEntry 6 }

		
		-- 1.3.6.1.4.1.32285.11.2.3.13.1.9.1.7
		topAAAServerTimeOut OBJECT-TYPE
			SYNTAX INTEGER (3..10)
			MAX-ACCESS read-write
			STATUS current
			DESCRIPTION
				"AAA server time out."
			DEFVAL { 3 }
			::= { topAAAServerEntry 7 }      
			    
		-- 1.3.6.1.4.1.32285.11.2.3.13.1.9.1.8

		topAAAServerHostIpv6 OBJECT-TYPE
			SYNTAX InetAddressIPv6
			MAX-ACCESS read-write
			STATUS current
			DESCRIPTION
				"AAA server ipv6 address."
			::= { topAAAServerEntry 8 } 
					
		-- 1.3.6.1.4.1.32285.11.2.3.13.2
		topAAADefaultGroupConfigObjects OBJECT IDENTIFIER ::= { topAAA 2 }

		
		-- 1.3.6.1.4.1.32285.11.2.3.13.2.1
		topAAADefaultGroupObjects OBJECT IDENTIFIER ::= { topAAADefaultGroupConfigObjects 1 }

		
		-- 1.3.6.1.4.1.32285.11.2.3.13.2.1.1
		topAAADefGrpLoginModList OBJECT-TYPE
			SYNTAX OCTET STRING (SIZE (5))
			MAX-ACCESS read-write
			STATUS current
			DESCRIPTION
				"The list of AAA default group login authentication method.
				 1 tacacs+ authentication method.
				 2 radius authentication method.
				 3 enable authentication method.
				 4 local authentication method.
				 5 none authentication method."
			::= { topAAADefaultGroupObjects 1 }

		
		-- 1.3.6.1.4.1.32285.11.2.3.13.2.1.2
		topAAADefGrpEnableModList OBJECT-TYPE
			SYNTAX OCTET STRING (SIZE (5))
			MAX-ACCESS read-write
			STATUS current
			DESCRIPTION
				"The list of AAA default group enable authentication method.
				 1 tacacs+ authentication method.
				 2 radius authentication method.
				 3 enable authentication method.
				 4 local authentication method.
				 5 none authentication method."
			::= { topAAADefaultGroupObjects 2 }

		
		-- 1.3.6.1.4.1.32285.11.2.3.13.2.1.3
		topAAADefGrpExecModList OBJECT-TYPE
			SYNTAX OCTET STRING (SIZE (5))
			MAX-ACCESS read-write
			STATUS current
			DESCRIPTION
				"The list of AAA default group login authorization method .
				 1 tacacs+ authentication method.
				 2 radius authentication method.
				 3 enable authentication method.
				 4 local authentication method.
				 5 none authentication method."
			::= { topAAADefaultGroupObjects 3 }

		
		-- 1.3.6.1.4.1.32285.11.2.3.13.2.2
		topAAADefaultGroupCmdAuthorTable OBJECT-TYPE
			SYNTAX SEQUENCE OF TopAAADefaultGroupCmdAuthorEntry
			MAX-ACCESS not-accessible
			STATUS current
			DESCRIPTION
				"AAA default group command authorization method table."
			::= { topAAADefaultGroupConfigObjects 2 }

		
		-- 1.3.6.1.4.1.32285.11.2.3.13.2.2.1
		topAAADefaultGroupCmdAuthorEntry OBJECT-TYPE
			SYNTAX TopAAADefaultGroupCmdAuthorEntry
			MAX-ACCESS not-accessible
			STATUS current
			DESCRIPTION
				"AAA default group command authorization method entry."
			INDEX { topAAADefGrpCmdLevelIndex }
			::= { topAAADefaultGroupCmdAuthorTable 1 }

		
		TopAAADefaultGroupCmdAuthorEntry ::=
			SEQUENCE { 
				topAAADefGrpCmdLevelIndex
					INTEGER,
				topAAADefGrpCmdModList
					OCTET STRING,
				topAAADefGrpCmdRowStatus
					RowStatus
			 }

		-- 1.3.6.1.4.1.32285.11.2.3.13.2.2.1.1
		topAAADefGrpCmdLevelIndex OBJECT-TYPE
			SYNTAX INTEGER (0..15)
			MAX-ACCESS not-accessible
			STATUS current
			DESCRIPTION
				"AAA default group user level."
			::= { topAAADefaultGroupCmdAuthorEntry 1 }

		
		-- 1.3.6.1.4.1.32285.11.2.3.13.2.2.1.2
		topAAADefGrpCmdModList OBJECT-TYPE
			SYNTAX OCTET STRING (SIZE (5))
			MAX-ACCESS read-write
			STATUS current
			DESCRIPTION
				"The list of AAA default group command authorization method.
				 1 tacacs+ authorization method.
				 4 local authorization method.
				 5 none authorization method."
			::= { topAAADefaultGroupCmdAuthorEntry 2 }

		
		-- 1.3.6.1.4.1.32285.11.2.3.13.2.2.1.3
		topAAADefGrpCmdRowStatus OBJECT-TYPE
			SYNTAX RowStatus
			MAX-ACCESS read-create
			STATUS current
			DESCRIPTION
				"Row Status. This object indicates the row status of this table:
				createAndGo(4): indicates that a row is created.
				destroy(6): indicates that a row is deleted."
			::= { topAAADefaultGroupCmdAuthorEntry 3 }
	
	
	END

	
--
-- SUMA-AAA-MIB.mib
--
