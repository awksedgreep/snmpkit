--
-- SUMA-EPONEOC-EPON-MIB.mib
-- MIB generated by MG-SOFT Visual MIB Builder Version 4.0 Build 349
-- Wednesday, October 19, 2011 at 15:54:31
--

	SUMA-EPONEOC-EPON-MIB DEFINITIONS ::= BEGIN
 
		IMPORTS
			enterprises, TimeTicks, IpAddress, Unsigned32, Counter64, 
			OBJECT-TYPE, OBJECT-IDENTITY			
				FROM SNMPv2-SMI			
			RowStatus, TimeStamp, DisplayString, MacAddress, TEXTUAL-CONVENTION			
				FROM SNMPv2-TC;
	
	
--
-- Textual conventions
--
	
		TopEponAlarmCode ::= TEXTUAL-CONVENTION
			STATUS current
			DESCRIPTION 
				"Alarm codes, uniquely indentifies each kind of alarm.
				Refer to EPON alarm definition table"
			SYNTAX INTEGER (1..65535)

		TopEPonSlotIndex ::= TEXTUAL-CONVENTION
			STATUS current
			DESCRIPTION 
				"This represents the slot number in the epon shelf."
			SYNTAX INTEGER (1..18)

		TopEPonPonIndex ::= TEXTUAL-CONVENTION
			STATUS current
			DESCRIPTION 
				"This represents the PON number in the epon board."
			SYNTAX INTEGER (1..8)

		EponDeviceIndex ::= TEXTUAL-CONVENTION
			STATUS current
			DESCRIPTION 
				"From MSB on, OLT slot index-8bits, PON/SNI port-8bits, 
				OnuNUM-8bits and UNI port-8bits.
				OLT PON/SNI Port - OnuNum and UNI port shall be set to 0."
			SYNTAX Unsigned32

		TopEPonOnuAuthNum ::= TEXTUAL-CONVENTION
			STATUS current
			DESCRIPTION 
				"This represents the ONU auth number in the epon board."
			SYNTAX INTEGER (1..128)

		TopEPonUniPortIndex ::= TEXTUAL-CONVENTION
			STATUS current
			DESCRIPTION 
				"This represents the ONU uni number in the epon board."
			SYNTAX INTEGER (1..32)

		TopEponStatsThresholdType ::= TEXTUAL-CONVENTION
			STATUS current
			DESCRIPTION 
				"1- InOctets
				2 InPkts
				3 InBroadcastPkts
				4 InMulticastPkts
				5 InPkts64Octets
				6 InPkts65to127Octets
				7 InPkts128to255Octets
				8 InPkts256to511Octets
				9 InPkts512to1023Octets
				10 InPkts1024to1518Octets
				11 InPkts1519to1522Octets
				12 InUndersizePkts
				13 InOversizePkts
				14 InFragments
				15 InMpcpFrames
				16 InMpcpOctets
				17 InOAMFrames
				18 InOAMOctets
				19 InCRCErrorPkts
				20 InDropEvents
				21 InJabbers
				22 InCollision
				23 OutOctets
				24 OutPkts
				25 OutBroadcastPkts
				26 OutMulticastPkts
				27 OutPkts64Octets
				28 OutPkts65to127Octets
				29 OutPkts128to255Octets
				30 OutPkts256to511Octets
				31 OutPkts512to1023Octets
				32 OutPkts1024to1518Octets
				33 OutPkts1519o1522Octets
				34 OutUndersizePkts
				35 OutOversizePkts
				36 OutFragments
				37 OutMpcpFrames
				38 OutMpcpOctets
				39 OutOAMFrames
				40 OutOAMOctets
				41 OutCRCErrorPkts
				42 OutDropEvents
				43 OutJabbers
				44 OutCollision
				50 Temperature
				Note:
				----------------------------------------------------------------
				1. For 50 Temperature, this parameter shall only applied to
				a. Slot level, for each service/switch/management card, for
				chassis-based system.
				b. Node-level, for fixed box.
				2. For 50 Temperature, shall be applied to both OLT and ONU
				3. For 50 Temperature, since no 15-min performance data collection
				are required, system shall ensure the temperature polling interval
				no less than 5 seconds. The alarm shall be only generated when the
				threshold is acrossed for three continuous intervals, and shall be
				cleared, when the threshold is not accrossed any more, for three
				continous intervals.
				"
			SYNTAX INTEGER (1..1024)

		TopEPonSniIndex ::= TEXTUAL-CONVENTION
			STATUS current
			DESCRIPTION 
				"This represents the sni port number in the uplink board."
			SYNTAX INTEGER (1..8)

	
--
-- Node definitions
--
	
		-- 1.3.6.1.4.1.32285
		sumaRoot OBJECT IDENTIFIER ::= { enterprises 32285 }

		
		-- 1.3.6.1.4.1.32285.11
		topvisionRoot OBJECT IDENTIFIER ::= { sumaRoot 11 }

		
		-- 1.3.6.1.4.1.32285.11.1
		topvisionHFCCcmtsTree OBJECT IDENTIFIER ::= { topvisionRoot 1 }

		
		-- 1.3.6.1.4.1.32285.11.2
		topvisionEponEocTree OBJECT IDENTIFIER ::= { topvisionRoot 2 }

		
		-- 1.3.6.1.4.1.32285.11.2.1
		propertyIdent OBJECT IDENTIFIER ::= { topvisionEponEocTree 1 }

		
		-- 1.3.6.1.4.1.32285.11.2.2
		topAlarmsIdent OBJECT IDENTIFIER ::= { topvisionEponEocTree 2 }

		
		-- 1.3.6.1.4.1.32285.11.2.2.11
		topEponAlarmTree OBJECT IDENTIFIER ::= { topAlarmsIdent 11 }

		
		-- 1.3.6.1.4.1.32285.11.2.2.11.4
		topEponAlarmMaskObjGroup OBJECT IDENTIFIER ::= { topEponAlarmTree 4 }

		
		-- 1.3.6.1.4.1.32285.11.2.2.11.4.1
		topAlarmCodeMaskTable OBJECT-TYPE
			SYNTAX SEQUENCE OF TopAlarmCodeMaskEntry
			MAX-ACCESS not-accessible
			STATUS current
			DESCRIPTION
				"alarm code mask config table"
			::= { topEponAlarmMaskObjGroup 1 }

		
		-- 1.3.6.1.4.1.32285.11.2.2.11.4.1.1
		topAlarmCodeMaskEntry OBJECT-TYPE
			SYNTAX TopAlarmCodeMaskEntry
			MAX-ACCESS not-accessible
			STATUS current
			DESCRIPTION
				"Alarm Code Mask config entry"
			INDEX { topAlarmCodeMaskIndex }
			::= { topAlarmCodeMaskTable 1 }

		
		TopAlarmCodeMaskEntry ::=
			SEQUENCE { 
				topAlarmCodeMaskIndex
					TopEponAlarmCode,
				topAlarmCodeMaskEnable
					INTEGER,
				topAlarmCodeMaskRowStatus
					RowStatus
			 }

		-- 1.3.6.1.4.1.32285.11.2.2.11.4.1.1.1
		topAlarmCodeMaskIndex OBJECT-TYPE
			SYNTAX TopEponAlarmCode
			MAX-ACCESS not-accessible
			STATUS current
			DESCRIPTION
				"Alarm code to be masked."
			::= { topAlarmCodeMaskEntry 1 }

		
		-- 1.3.6.1.4.1.32285.11.2.2.11.4.1.1.2
		topAlarmCodeMaskEnable OBJECT-TYPE
			SYNTAX INTEGER
				{
				enable(1),
				disable(2)
				}
			MAX-ACCESS read-write
			STATUS current
			DESCRIPTION
				"enalbe / disable"
			::= { topAlarmCodeMaskEntry 2 }

		
		-- 1.3.6.1.4.1.32285.11.2.2.11.4.1.1.3
		topAlarmCodeMaskRowStatus OBJECT-TYPE
			SYNTAX RowStatus
			MAX-ACCESS read-write
			STATUS current
			DESCRIPTION
				"add/del/set"
			::= { topAlarmCodeMaskEntry 3 }

		
		-- 1.3.6.1.4.1.32285.11.2.2.11.4.2
		topAlarmInstanceMaskTable OBJECT-TYPE
			SYNTAX SEQUENCE OF TopAlarmInstanceMaskEntry
			MAX-ACCESS not-accessible
			STATUS current
			DESCRIPTION
				"alarm instance mask config table"
			::= { topEponAlarmMaskObjGroup 2 }

		
		-- 1.3.6.1.4.1.32285.11.2.2.11.4.2.1
		topAlarmInstanceMaskEntry OBJECT-TYPE
			SYNTAX TopAlarmInstanceMaskEntry
			MAX-ACCESS not-accessible
			STATUS current
			DESCRIPTION
				"Alarm Mask config entry"
			INDEX { topAlarmInstanceMaskIndex }
			::= { topAlarmInstanceMaskTable 1 }

		
		TopAlarmInstanceMaskEntry ::=
			SEQUENCE { 
				topAlarmInstanceMaskIndex
					INTEGER,
				topAlarmInstanceMaskEnable
					INTEGER,
				topAlarmInstanceMaskRowStatus
					RowStatus
			 }

		-- 1.3.6.1.4.1.32285.11.2.2.11.4.2.1.1
		topAlarmInstanceMaskIndex OBJECT-TYPE
			SYNTAX INTEGER
			MAX-ACCESS not-accessible
			STATUS current
			DESCRIPTION
				"Alarm instance, indicates the detailed managed object.
				The MSB byte is slot index, then PON index, ONU-AUTH number,
				the LSB byte is uniPort index. 0 indicates meaningless.
				for instance, 0x01010000 means slot=1 and pon=1."
			::= { topAlarmInstanceMaskEntry 1 }

		
		-- 1.3.6.1.4.1.32285.11.2.2.11.4.2.1.2
		topAlarmInstanceMaskEnable OBJECT-TYPE
			SYNTAX INTEGER
				{
				enable(1),
				disable(2)
				}
			MAX-ACCESS read-write
			STATUS current
			DESCRIPTION
				"C"
			::= { topAlarmInstanceMaskEntry 2 }

		
		-- 1.3.6.1.4.1.32285.11.2.2.11.4.2.1.3
		topAlarmInstanceMaskRowStatus OBJECT-TYPE
			SYNTAX RowStatus
			MAX-ACCESS read-write
			STATUS current
			DESCRIPTION
				"add/del/set"
			::= { topAlarmInstanceMaskEntry 3 }

		
		-- 1.3.6.1.4.1.32285.11.2.2.11.5
		topEponAlarmGlobalConfigObj OBJECT IDENTIFIER ::= { topEponAlarmTree 5 }

		
		-- 1.3.6.1.4.1.32285.11.2.2.11.5.1
		topEponAlarmMode OBJECT-TYPE
			SYNTAX INTEGER
			MAX-ACCESS read-write
			STATUS current
			DESCRIPTION
				"set the alarm support mode
				MSB-BYTE 2nd-BYTE 3rd-BYTE LSB-BYTE | description
				  0x00     0x00     0x01     0x01   | Internal standards
				  0x00     0x00     0x01     0x02   | NSCRTV standards
				  0x00     0x00     0x01     0x03   | CTC standards"
			DEFVAL { '00000102'h }
			::= { topEponAlarmGlobalConfigObj 1 }
			
			
		-- 1.3.6.1.4.1.32285.11.2.3
		topvisionEponTree OBJECT IDENTIFIER ::= { topvisionEponEocTree 3 }

		
		-- 1.3.6.1.4.1.32285.11.2.3.1
		topSystemObjects OBJECT IDENTIFIER ::= { topvisionEponTree 1 }

		
		-- 1.3.6.1.4.1.32285.11.2.3.1.1
		topSysGlobalObjects OBJECT IDENTIFIER ::= { topSystemObjects 1 }

		
		-- 1.3.6.1.4.1.32285.11.2.3.1.1.1
		topSysSnmpHostIp OBJECT-TYPE
			SYNTAX IpAddress
			MAX-ACCESS read-write
			STATUS current
			DESCRIPTION
				"SNMP Host Ip Address"
			::= { topSysGlobalObjects 1 }

		
		-- 1.3.6.1.4.1.32285.11.2.3.1.1.2
		topSysSnmpHostIpMask OBJECT-TYPE
			SYNTAX IpAddress
			MAX-ACCESS read-write
			STATUS current
			DESCRIPTION
				"IP address mask"
			::= { topSysGlobalObjects 2 }

		
		-- 1.3.6.1.4.1.32285.11.2.3.1.1.3
		topSysSnmpVersion OBJECT-TYPE
			SYNTAX INTEGER
				{
				snmpv1(1),
				snmpv2c(2),
				snmpv3(3)
				}
			MAX-ACCESS read-write
			STATUS current
			DESCRIPTION
				"The version of the Trap PDUs forwarded to the host.
				v2 supported only."
			DEFVAL { 2 }
			::= { topSysGlobalObjects 3 }

		
		-- 1.3.6.1.4.1.32285.11.2.3.1.1.4
		topSysReadCommunity OBJECT-TYPE
			SYNTAX OCTET STRING (SIZE (1..63))
			MAX-ACCESS read-write
			STATUS current
			DESCRIPTION
				"snmp read community"
			DEFVAL { "public" }
			::= { topSysGlobalObjects 4 }

		
		-- 1.3.6.1.4.1.32285.11.2.3.1.1.5
		topSysWriteCommunity OBJECT-TYPE
			SYNTAX OCTET STRING (SIZE (1..63))
			MAX-ACCESS read-write
			STATUS current
			DESCRIPTION
				"snmp write community"
			DEFVAL { "private" }
			::= { topSysGlobalObjects 5 }

		
		-- 1.3.6.1.4.1.32285.11.2.3.1.1.6
		topSysSnmpPort OBJECT-TYPE
			SYNTAX INTEGER (161 | 1025..65534)
			MAX-ACCESS read-write
			STATUS current
			DESCRIPTION
				"not supported at present."
			::= { topSysGlobalObjects 6 }

		
		-- 1.3.6.1.4.1.32285.11.2.3.1.1.7
		topSysInBandMaxBW OBJECT-TYPE
			SYNTAX INTEGER (1..3000)
			UNITS "pps"
			MAX-ACCESS read-write
			STATUS current
			DESCRIPTION
				"Max bandwidth, unit:pps"
			::= { topSysGlobalObjects 7 }

		
		-- 1.3.6.1.4.1.32285.11.2.3.1.2
		topSysOltObjects OBJECT IDENTIFIER ::= { topSystemObjects 2 }

		
		-- 1.3.6.1.4.1.32285.11.2.3.1.2.1
		topSysOltRackNum OBJECT-TYPE
			SYNTAX INTEGER
			MAX-ACCESS read-write
			STATUS current
			DESCRIPTION
				"ID of the cabinet, which contains the cuurent OLT.
				Staring index is 1."
			::= { topSysOltObjects 1 }

		
		-- 1.3.6.1.4.1.32285.11.2.3.1.2.2
		topSysOltFrameNum OBJECT-TYPE
			SYNTAX INTEGER
			MAX-ACCESS read-write
			STATUS current
			DESCRIPTION
				"ID of the OLT frame, which indicate the index or postion 
				in the current cabinet, and started with 1."
			::= { topSysOltObjects 2 }

		
		-- 1.3.6.1.4.1.32285.11.2.3.1.2.3
		topSysOltSave OBJECT-TYPE
			SYNTAX INTEGER
				{
				noOperation(0),
				save(1)
				}
			MAX-ACCESS read-write
			STATUS current
			DESCRIPTION
				"save(1) current config to OLT, and noOperation(0),
				other values are reserved."
			::= { topSysOltObjects 3 }

		
		-- 1.3.6.1.4.1.32285.11.2.3.1.2.4
		topSysOltSaveStatus OBJECT-TYPE
			SYNTAX INTEGER
				{
				saving(1),
				savedOrReady(2),
				savedFail(3)
				}
			MAX-ACCESS read-only
			STATUS current
			DESCRIPTION
				"save status. saving(1) represent in progress of saving operation,
				saved(2) represent completion of saving operation,
				savedFail(3) represent failure of saving operation."
			::= { topSysOltObjects 4 }

		
		-- 1.3.6.1.4.1.32285.11.2.3.1.2.5
		topSysOltReset OBJECT-TYPE
			SYNTAX INTEGER
				{
				noOperation(0),
				reset(1)
				}
			MAX-ACCESS read-write
			STATUS current
			DESCRIPTION
				"Reset OLT system, including MPU and all other boards under this OLT.
				noOperation(0), and other values are reserved."
			::= { topSysOltObjects 5 }

		
		-- 1.3.6.1.4.1.32285.11.2.3.1.2.6
		topSysOltRestoreFactoryConfig OBJECT-TYPE
			SYNTAX INTEGER
				{
				noOperation(0),
				restore(1)
				}
			MAX-ACCESS read-write
			STATUS current
			DESCRIPTION
				"Description."
			DEFVAL { 0 }
			::= { topSysOltObjects 6 }

		
		-- 1.3.6.1.4.1.32285.11.2.3.1.3
		topSysBoardObjects OBJECT IDENTIFIER ::= { topSystemObjects 3 }

		
		-- 1.3.6.1.4.1.32285.11.2.3.1.3.1
		topSysBoardTable OBJECT-TYPE
			SYNTAX SEQUENCE OF TopSysBoardEntry
			MAX-ACCESS not-accessible
			STATUS current
			DESCRIPTION
				"This table shall include rows for all slots, including the slots has
				a presence state of 'NotInstalled'. In case of board absence, 
				return 0."
			::= { topSysBoardObjects 1 }

		
		-- 1.3.6.1.4.1.32285.11.2.3.1.3.1.1
		topSysBoardEntry OBJECT-TYPE
			SYNTAX TopSysBoardEntry
			MAX-ACCESS not-accessible
			STATUS current
			DESCRIPTION
				"The slot number within the epon chassis. This is used
				as the index into topSysBoardEntry."
			INDEX { topSysBdSlotIndex }
			::= { topSysBoardTable 1 }

		
		TopSysBoardEntry ::=
			SEQUENCE { 
				topSysBdSlotIndex
					TopEPonSlotIndex,
				topSysBdPreConfigType
					INTEGER,
				topSysBdActualType
					INTEGER,
				topSysBdCPUUseRatio
					INTEGER,
				topSysBdlMemSize
					INTEGER,
				topSysBdFreeMemSize
					INTEGER,
				topSysBdTotalFlashOctets
					INTEGER,
				topSysBdFreeFlashOctets
					INTEGER,
				topSysBdCurrentTemperature
					INTEGER,
				topSysBdTempDetectEnable
					INTEGER,
				topSysBdLampStatus
					INTEGER,
				topSysBdReset
					INTEGER
			 }

		-- 1.3.6.1.4.1.32285.11.2.3.1.3.1.1.1
		topSysBdSlotIndex OBJECT-TYPE
			SYNTAX TopEPonSlotIndex
			MAX-ACCESS not-accessible
			STATUS current
			DESCRIPTION
				"The slot number within the epon chassis. This is used
				as the index into eponSlotStatustable."
			::= { topSysBoardEntry 1 }

		
		-- 1.3.6.1.4.1.32285.11.2.3.1.3.1.1.2
		topSysBdPreConfigType OBJECT-TYPE
			SYNTAX INTEGER
				{
				non-board(0),
				mpua(1),
				mpub(2),
				epua(3),
				epub(4),
				geua(5),
				geub(6),
				xgua(7),
				xgub(8),
				unknown(255)
				}
			MAX-ACCESS read-write
			STATUS current
			DESCRIPTION
				"This object provides the model of the card actually inserted
				into the corresponding slot in the chassis. Only the first byte
				in this integer value is available."
			::= { topSysBoardEntry 2 }

		
		-- 1.3.6.1.4.1.32285.11.2.3.1.3.1.1.3
		topSysBdActualType OBJECT-TYPE
			SYNTAX INTEGER
				{
				non-board(0),
				mpua(1),
				mpub(2),
				epua(3),
				epub(4),
				geua(5),
				geub(6),
				xgua(7),
				xgub(8),
				unknown(255)
				}
			MAX-ACCESS read-only
			STATUS current
			DESCRIPTION
				"actual board type"
			::= { topSysBoardEntry 3 }

		
		-- 1.3.6.1.4.1.32285.11.2.3.1.3.1.1.4
		topSysBdCPUUseRatio OBJECT-TYPE
			SYNTAX INTEGER (1..100)
			MAX-ACCESS read-only
			STATUS current
			DESCRIPTION
				"The using ratio of the CPU."
			::= { topSysBoardEntry 4 }

		
		-- 1.3.6.1.4.1.32285.11.2.3.1.3.1.1.5
		topSysBdlMemSize OBJECT-TYPE
			SYNTAX INTEGER
			MAX-ACCESS read-only
			STATUS current
			DESCRIPTION
				"The total memory size in MB."
			::= { topSysBoardEntry 5 }

		
		-- 1.3.6.1.4.1.32285.11.2.3.1.3.1.1.6
		topSysBdFreeMemSize OBJECT-TYPE
			SYNTAX INTEGER
			MAX-ACCESS read-only
			STATUS current
			DESCRIPTION
				"The free memory size in MPUA and EPUA,in units of byte."
			::= { topSysBoardEntry 6 }

		
		-- 1.3.6.1.4.1.32285.11.2.3.1.3.1.1.7
		topSysBdTotalFlashOctets OBJECT-TYPE
			SYNTAX INTEGER
			MAX-ACCESS read-only
			STATUS current
			DESCRIPTION
				"The total size of the flash in MCU or LPU,in units of kilo byte."
			::= { topSysBoardEntry 7 }

		
		-- 1.3.6.1.4.1.32285.11.2.3.1.3.1.1.8
		topSysBdFreeFlashOctets OBJECT-TYPE
			SYNTAX INTEGER
			MAX-ACCESS read-only
			STATUS current
			DESCRIPTION
				"The total size of the flash in MCU or LPU,in units of kilo byte."
			::= { topSysBoardEntry 8 }

		
		-- 1.3.6.1.4.1.32285.11.2.3.1.3.1.1.9
		topSysBdCurrentTemperature OBJECT-TYPE
			SYNTAX INTEGER
			MAX-ACCESS read-only
			STATUS current
			DESCRIPTION
				"The current temprature"
			::= { topSysBoardEntry 9 }

		
		-- 1.3.6.1.4.1.32285.11.2.3.1.3.1.1.10
		topSysBdTempDetectEnable OBJECT-TYPE
			SYNTAX INTEGER
				{
				enable(1),
				disable(2)
				}
			MAX-ACCESS read-write
			STATUS current
			DESCRIPTION
				"enable/disable temprature detecting"
			::= { topSysBoardEntry 10 }

		
		-- 1.3.6.1.4.1.32285.11.2.3.1.3.1.1.11
		topSysBdLampStatus OBJECT-TYPE
			SYNTAX INTEGER
			MAX-ACCESS read-only
			STATUS current
			DESCRIPTION
				"LAMP status.
				BOARD-TYPE  MSB-BYTE 2nd-BYTE 3rd-BYTE LSB-BYTE
				MPU         MS       RUN      ALARM    reserved
				EPU         reserved RUN      ALARM    reserved
				GEUA        reserved RUN      ALARM    reserved
				XGUA        reserved RUN      ALARM    reserved
				FAN         reserved RUN      ALARM    reserved
				for each byte, 
				1-master, 0-slave
				1-running, 2-loading.
				1-no alarm, 2-alarm.
				the reserved bytes are set to 0."
			::= { topSysBoardEntry 11 }

		
		-- 1.3.6.1.4.1.32285.11.2.3.1.3.1.1.12
		topSysBdReset OBJECT-TYPE
			SYNTAX INTEGER
				{
				noOperation(0),
				reset(1)
				}
			MAX-ACCESS read-write
			STATUS current
			DESCRIPTION
				"reset(1) board, noOperation(0), other values are reserved."
			::= { topSysBoardEntry 12 }


		-- 1.3.6.1.4.1.32285.11.2.3.1.3.1.2
		topSysBoardMapTable OBJECT-TYPE
			SYNTAX SEQUENCE OF TopSysBoardMapEntry
			MAX-ACCESS not-accessible
			STATUS current
			DESCRIPTION
				"This table is for physical slot mapping to logic slot only."
			::= { topSysBoardObjects 2 }

		
		-- 1.3.6.1.4.1.32285.11.2.3.1.3.1.2
		topSysBoardMapEntry OBJECT-TYPE
			SYNTAX TopSysBoardMapEntry
			MAX-ACCESS not-accessible
			STATUS current
			DESCRIPTION
				"The slot number within the epon chassis. This is used
				as the index into topSysBoardMapEntry."
			INDEX { topSysBdMapPhySlotIndex }
			::= { topSysBoardMapTable 1 }

		
		TopSysBoardMapEntry ::=
			SEQUENCE { 
				topSysBdMapPhySlotIndex
					TopEPonSlotIndex,
				topSysBdMapLogSlot
					INTEGER
			 }

		-- 1.3.6.1.4.1.32285.11.2.3.1.3.1.2.1
		topSysBdMapPhySlotIndex OBJECT-TYPE
			SYNTAX TopEPonSlotIndex
			MAX-ACCESS not-accessible
			STATUS current
			DESCRIPTION
				"The slot number within the epon chassis. This is used
				as the index into eponSlotStatustable."
			::= { topSysBoardMapEntry 1 }

		-- 1.3.6.1.4.1.32285.11.2.3.1.3.1.2.2
		topSysBdMapLogSlot OBJECT-TYPE
			SYNTAX INTEGER
			MAX-ACCESS read-only
			STATUS current
			DESCRIPTION
				"0-logical slot number of the current active master control board,
				for instance, logical slot 0 present for physical slot 9&10.
				this table will allowed to access on the basis of physical slot only,
				but all other service will be on the basis of logical slot."
			::= { topSysBoardMapEntry 2 }

		
		-- 1.3.6.1.4.1.32285.11.2.3.1.4
		topSysPowerObjects OBJECT IDENTIFIER ::= { topSystemObjects 4 }

		
		-- 1.3.6.1.4.1.32285.11.2.3.1.4.1
		topSysPowerPropertyTable OBJECT-TYPE
			SYNTAX SEQUENCE OF TopSysPowerPropertyEntry
			MAX-ACCESS not-accessible
			STATUS current
			DESCRIPTION
				"power management"
			::= { topSysPowerObjects 1 }

		
		-- 1.3.6.1.4.1.32285.11.2.3.1.4.1.1
		topSysPowerPropertyEntry OBJECT-TYPE
			SYNTAX TopSysPowerPropertyEntry
			MAX-ACCESS not-accessible
			STATUS current
			DESCRIPTION
				"power management entry"
			INDEX { topSysPowerCardIndex }
			::= { topSysPowerPropertyTable 1 }

		
		TopSysPowerPropertyEntry ::=
			SEQUENCE { 
				topSysPowerCardIndex
					INTEGER,
				topSysPowerSupplyType
					INTEGER,
				topSysPowerSupplyACVoltage
					INTEGER,
				topSysPowerSupplyACTemperature
					INTEGER
			 }

		-- 1.3.6.1.4.1.32285.11.2.3.1.4.1.1.1
		topSysPowerCardIndex OBJECT-TYPE
			SYNTAX INTEGER (20..21)
			MAX-ACCESS not-accessible
			STATUS current
			DESCRIPTION
				"power slot is 20,21"
			::= { topSysPowerPropertyEntry 1 }

		
		-- 1.3.6.1.4.1.32285.11.2.3.1.4.1.1.2
		topSysPowerSupplyType OBJECT-TYPE
			SYNTAX INTEGER
				{
				powerDC(1),
				powerAC(2)
				}
			MAX-ACCESS read-only
			STATUS current
			DESCRIPTION
				"DC-1;AC-2"
			::= { topSysPowerPropertyEntry 2 }

		
		-- 1.3.6.1.4.1.32285.11.2.3.1.4.1.1.3
		topSysPowerSupplyACVoltage OBJECT-TYPE
			SYNTAX INTEGER
			MAX-ACCESS read-only
			STATUS current
			DESCRIPTION
				"AC power voltage"
			::= { topSysPowerPropertyEntry 3 }

		
		-- 1.3.6.1.4.1.32285.11.2.3.1.4.1.1.4
		topSysPowerSupplyACTemperature OBJECT-TYPE
			SYNTAX INTEGER
			MAX-ACCESS read-only
			STATUS current
			DESCRIPTION
				"AC power temperature"
			::= { topSysPowerPropertyEntry 4 }

		
		-- 1.3.6.1.4.1.32285.11.2.3.1.5
		topSysFanObjects OBJECT IDENTIFIER ::= { topSystemObjects 5 }

		
		-- 1.3.6.1.4.1.32285.11.2.3.1.5.1
		topSysFanPropertyTable OBJECT-TYPE
			SYNTAX SEQUENCE OF TopSysFanPropertyEntry
			MAX-ACCESS not-accessible
			STATUS current
			DESCRIPTION
				"fan management"
			::= { topSysFanObjects 1 }

		
		-- 1.3.6.1.4.1.32285.11.2.3.1.5.1.1
		topSysFanPropertyEntry OBJECT-TYPE
			SYNTAX TopSysFanPropertyEntry
			MAX-ACCESS not-accessible
			STATUS current
			DESCRIPTION
				"fan management entry "
			INDEX { topSysFanCardIndex, topSysFanIndex }
			::= { topSysFanPropertyTable 1 }

		
		TopSysFanPropertyEntry ::=
			SEQUENCE { 
				topSysFanCardIndex
					INTEGER,
				topSysFanIndex
					INTEGER,
				topSysFanSpeedControl
					INTEGER,
				topSysFanSpeed
					INTEGER,
				topSysFanLampStatus
					INTEGER
			 }

		-- 1.3.6.1.4.1.32285.11.2.3.1.5.1.1.1
		topSysFanCardIndex OBJECT-TYPE
			SYNTAX INTEGER (19)
			MAX-ACCESS not-accessible
			STATUS current
			DESCRIPTION
				"fan slot index"
			::= { topSysFanPropertyEntry 1 }

		
		-- 1.3.6.1.4.1.32285.11.2.3.1.5.1.1.2
		topSysFanIndex OBJECT-TYPE
			SYNTAX INTEGER (1..3)
			MAX-ACCESS not-accessible
			STATUS current
			DESCRIPTION
				"fan slot index"
			::= { topSysFanPropertyEntry 2 }

		
		-- 1.3.6.1.4.1.32285.11.2.3.1.5.1.1.3
		topSysFanSpeedControl OBJECT-TYPE
			SYNTAX INTEGER
				{
				autoSpeed(1),
				lowSpeed(2),
				middleSpeed(3),
				highSpeed(4)
				}
			MAX-ACCESS read-write
			STATUS current
			DESCRIPTION
				"fan speed level"
			::= { topSysFanPropertyEntry 3 }

		
		-- 1.3.6.1.4.1.32285.11.2.3.1.5.1.1.4
		topSysFanSpeed OBJECT-TYPE
			SYNTAX INTEGER
			MAX-ACCESS read-only
			STATUS current
			DESCRIPTION
				"fan speed unit:rps"
			::= { topSysFanPropertyEntry 4 }

		
		-- 1.3.6.1.4.1.32285.11.2.3.1.5.1.1.5
		topSysFanLampStatus OBJECT-TYPE
			SYNTAX INTEGER
			MAX-ACCESS read-only
			STATUS current
			DESCRIPTION
				"LAMP status.
				BOARD-TYPE  MSB-BYTE 2nd-BYTE 3rd-BYTE LSB-BYTE
				FAN         reserved RUN      ALARM    reserved
				for each byte, 
				2nd-BYTE    1-running, 2-loading.
				3rd-BYTE    1-no alarm, 2-alarm.
				the reserved bytes are set to 0."
			::= { topSysFanPropertyEntry 5 }

		
		-- 1.3.6.1.4.1.32285.11.2.3.1.6
		topSysHaMgmtObjects OBJECT IDENTIFIER ::= { topSystemObjects 6 }

		
		-- 1.3.6.1.4.1.32285.11.2.3.1.6.1
		topSysMasterSlotNum OBJECT-TYPE
			SYNTAX INTEGER (9..10)
			MAX-ACCESS read-only
			STATUS current
			DESCRIPTION
				"The number of slot which this mcu resides in."
			::= { topSysHaMgmtObjects 1 }

		
		-- 1.3.6.1.4.1.32285.11.2.3.1.6.2
		topSysMasterSlaveSynAction OBJECT-TYPE
			SYNTAX INTEGER
				{
				noOperation(0), 
				syncApp(1),
				syncConfig(2)
				}
			MAX-ACCESS read-write
			STATUS current
			DESCRIPTION
				"Sync app soft or config for master to slave."
			::= { topSysHaMgmtObjects 2 }
			
		
		-- 1.3.6.1.4.1.32285.11.2.3.1.6.3
		topSysMasterSlaveSyncStatus OBJECT-TYPE
			SYNTAX INTEGER
				{
				idle(0),
				syncAppInprogress(1),
				syncCfgInprogress(2),
				syncAppFail(3),
				syncAppSucc(4),
				syncCfgFail(5),
				syncCfgSucc(6)
				}
			MAX-ACCESS read-only
			STATUS current
			DESCRIPTION
				"sync status."
			::= { topSysHaMgmtObjects 3 }

		-- 1.3.6.1.4.1.32285.11.2.3.1.7
		topSysErrInfoObjects OBJECT IDENTIFIER ::= { topSystemObjects 7 }

		-- 1.3.6.1.4.1.32285.11.2.3.1.7.1
		topSysErrInfoTable OBJECT-TYPE
			SYNTAX SEQUENCE OF TopSysErrInfoEntry
			MAX-ACCESS not-accessible
			STATUS current
			DESCRIPTION
				"error code information."
			::= { topSysErrInfoObjects 1 }
				
		-- 1.3.6.1.4.1.32285.11.2.3.1.7.1.1
		topSysErrInfoEntry OBJECT-TYPE
			SYNTAX TopSysErrInfoEntry
			MAX-ACCESS not-accessible
			STATUS current
			DESCRIPTION
				"error code information entry."
			INDEX { topSysErrInfoLangIndex, topSysErrInfoIdIndex }
			::= { topSysErrInfoTable 1 }
		TopSysErrInfoEntry ::=
			SEQUENCE { 
				topSysErrInfoLangIndex
					INTEGER,
				topSysErrInfoIdIndex
					INTEGER,
				topSysErrInfoDescription
					OCTET STRING
			 }
			 
		-- 1.3.6.1.4.1.32285.11.2.3.1.7.1.1.1
		topSysErrInfoLangIndex OBJECT-TYPE
			SYNTAX INTEGER (0..255)
			MAX-ACCESS not-accessible
			STATUS current
			DESCRIPTION
				"error information language index: English(0), Simplified Chinese(1), Traditional Chinese(2)."
			::= { topSysErrInfoEntry 1 }
			
		-- 1.3.6.1.4.1.32285.11.2.3.1.7.1.1.2
		topSysErrInfoIdIndex OBJECT-TYPE
			SYNTAX INTEGER (1025..16777216)
			MAX-ACCESS not-accessible
			STATUS current
			DESCRIPTION
				"error information id index."
			::= { topSysErrInfoEntry 2 }

		-- 1.3.6.1.4.1.32285.11.2.3.1.7.1.1.3
		topSysErrInfoDescription OBJECT-TYPE
			SYNTAX OCTET STRING (SIZE (1..63))
			MAX-ACCESS read-only
			STATUS current
			DESCRIPTION
				"error information description."
			::= { topSysErrInfoEntry 3 }

		
--  1.3.6.1.4.1.32285.11.2.3.2
		-- 1.3.6.1.4.1.32285.11.2.3.2
		topSniObjects OBJECT IDENTIFIER ::= { topvisionEponTree 2 }

		
		-- 1.3.6.1.4.1.32285.11.2.3.2.1
		topSniAttributeTable OBJECT-TYPE
			SYNTAX SEQUENCE OF TopSniAttributeEntry
			MAX-ACCESS not-accessible
			STATUS current
			DESCRIPTION
				"A list of topSniAttributeTable entries. "
			::= { topSniObjects 1 }

		
		-- 1.3.6.1.4.1.32285.11.2.3.2.1.1
		topSniAttributeEntry OBJECT-TYPE
			SYNTAX TopSniAttributeEntry
			MAX-ACCESS not-accessible
			STATUS current
			DESCRIPTION
				"The topSniAttributeEntry Information"
			INDEX { topSniAttrCardIndex, topSniAttrPortIndex }
			::= { topSniAttributeTable 1 }

		
		TopSniAttributeEntry ::=
			SEQUENCE { 
				topSniAttrCardIndex
					INTEGER,
				topSniAttrPortIndex
					INTEGER,
				topSniAttrFlowCtrlEnable
					INTEGER,
				topSniAttrIngressRate
					INTEGER,
				topSniAttrEgressRate
					INTEGER,
				topSniAttrActualSpeed
					Unsigned32,
				topSniAttrPortType
					INTEGER
			 }

		-- 1.3.6.1.4.1.32285.11.2.3.2.1.1.1
		topSniAttrCardIndex OBJECT-TYPE
			SYNTAX INTEGER (0..18)
			MAX-ACCESS not-accessible
			STATUS current
			DESCRIPTION
				"Card Index"
			::= { topSniAttributeEntry 1 }

		
		-- 1.3.6.1.4.1.32285.11.2.3.2.1.1.2
		topSniAttrPortIndex OBJECT-TYPE
			SYNTAX INTEGER
			MAX-ACCESS not-accessible
			STATUS current
			DESCRIPTION
				"Port Index"
			::= { topSniAttributeEntry 2 }

		
		-- 1.3.6.1.4.1.32285.11.2.3.2.1.1.3
		topSniAttrFlowCtrlEnable OBJECT-TYPE
			SYNTAX INTEGER
				{
				enable(1),
				disable(2)
				}
			MAX-ACCESS read-write
			STATUS current
			DESCRIPTION
				"Flow control en/disable"
			DEFVAL { 2 }
			::= { topSniAttributeEntry 3 }

		
		-- 1.3.6.1.4.1.32285.11.2.3.2.1.1.4
		topSniAttrIngressRate OBJECT-TYPE
			SYNTAX INTEGER
			UNITS "kbps"
			MAX-ACCESS read-write
			STATUS current
			DESCRIPTION
				"rate limit. unit:kbps"
			DEFVAL { '0'b }
			::= { topSniAttributeEntry 4 }

		
		-- 1.3.6.1.4.1.32285.11.2.3.2.1.1.5
		topSniAttrEgressRate OBJECT-TYPE
			SYNTAX INTEGER
			UNITS "kbps"
			MAX-ACCESS read-write
			STATUS current
			DESCRIPTION
				"rate limit. unit:kbps"
			DEFVAL { '0'b }
			::= { topSniAttributeEntry 5 }

		
		-- 1.3.6.1.4.1.32285.11.2.3.2.1.1.6
		topSniAttrActualSpeed OBJECT-TYPE
			SYNTAX Unsigned32
			UNITS "kbps"
			MAX-ACCESS read-only
			STATUS current
			DESCRIPTION
				"port actual speed "
			DEFVAL { 0 }
			::= { topSniAttributeEntry 6 }

		
		-- 1.3.6.1.4.1.32285.11.2.3.2.1.1.7
		topSniAttrPortType OBJECT-TYPE
			SYNTAX INTEGER
				{
				geCopper(1),
				geFiber(2),
				xeFiber(3)
				}
			MAX-ACCESS read-only
			STATUS current
			DESCRIPTION
				"sni port type"
			DEFVAL { 1 }
			::= { topSniAttributeEntry 7 }

		
		-- 1.3.6.1.4.1.32285.11.2.3.2.2
		topSniRedirectTable OBJECT-TYPE
			SYNTAX SEQUENCE OF TopSniRedirectEntry
			MAX-ACCESS not-accessible
			STATUS current
			DESCRIPTION
				"a list of topSniRedirectTable entries."
			::= { topSniObjects 2 }

		
		-- 1.3.6.1.4.1.32285.11.2.3.2.2.1
		topSniRedirectEntry OBJECT-TYPE
			SYNTAX TopSniRedirectEntry
			MAX-ACCESS not-accessible
			STATUS current
			DESCRIPTION
				"The Redirect Information."
			INDEX { topSniRedirectGroupSrcPort }
			::= { topSniRedirectTable 1 }

		
		TopSniRedirectEntry ::=
			SEQUENCE { 
				topSniRedirectGroupSrcPort
					INTEGER,
				topSniRedirectGroupDirection
					INTEGER,
				topSniRedirectGroupName
					DisplayString,
				topSniRedirectGroupDstPort
					INTEGER,
				topSniRedirectGroupRowstatus
					RowStatus
			 }

		-- 1.3.6.1.4.1.32285.11.2.3.2.2.1.1
		topSniRedirectGroupSrcPort OBJECT-TYPE
			SYNTAX INTEGER
			MAX-ACCESS not-accessible
			STATUS current
			DESCRIPTION
				"Redirect Group source port.
				The highest byte is SLOT index, then port index.
				the lowest byte reserved 0."
			::= { topSniRedirectEntry 1 }

		
		-- 1.3.6.1.4.1.32285.11.2.3.2.2.1.2
		topSniRedirectGroupDirection OBJECT-TYPE
			SYNTAX INTEGER
				{
				ingress(1),
				egress(2),
				biDirection(3)
				}
			MAX-ACCESS read-create
			STATUS current
			DESCRIPTION
				"direction"
			::= { topSniRedirectEntry 2 }

		
		-- 1.3.6.1.4.1.32285.11.2.3.2.2.1.3
		topSniRedirectGroupName OBJECT-TYPE
			SYNTAX DisplayString (SIZE (1..63))
			MAX-ACCESS read-create
			STATUS current
			DESCRIPTION
				"Redirect Group description"
			DEFVAL { "REDIRECT_GROUP_1" }
			::= { topSniRedirectEntry 3 }

		
		-- 1.3.6.1.4.1.32285.11.2.3.2.2.1.4
		topSniRedirectGroupDstPort OBJECT-TYPE
			SYNTAX INTEGER
			MAX-ACCESS read-create
			STATUS current
			DESCRIPTION
				"Redirect Group destination port.
				The highest byte is SLOT index, port index.
				the lowest two bytes are reserved 0."
			::= { topSniRedirectEntry 4 }

		
		-- 1.3.6.1.4.1.32285.11.2.3.2.2.1.5
		topSniRedirectGroupRowstatus OBJECT-TYPE
			SYNTAX RowStatus
			MAX-ACCESS read-create
			STATUS current
			DESCRIPTION
				"Redirect Group Rowstatus"
			::= { topSniRedirectEntry 5 }

		
		-- 1.3.6.1.4.1.32285.11.2.3.3
		topPonPortObjects OBJECT IDENTIFIER ::= { topvisionEponTree 3 }

		
		-- 1.3.6.1.4.1.32285.11.2.3.3.1
		topPonProtectMgmtObjects OBJECT IDENTIFIER ::= { topPonPortObjects 1 }

		
		-- 1.3.6.1.4.1.32285.11.2.3.3.1.1
		topPonProtectParamTemplateTable OBJECT-TYPE
			SYNTAX SEQUENCE OF TopPonProtectParamTemplateEntry
			MAX-ACCESS not-accessible
			STATUS current
			DESCRIPTION
				"protect setting parameter template of PON protect"
			::= { topPonProtectMgmtObjects 1 }

		
		-- 1.3.6.1.4.1.32285.11.2.3.3.1.1.1
		topPonProtectParamTemplateEntry OBJECT-TYPE
			SYNTAX TopPonProtectParamTemplateEntry
			MAX-ACCESS not-accessible
			STATUS current
			DESCRIPTION
				"protect setting parameter entry of PON protect"
			INDEX { topPonProtectParamTemplateIndex }
			::= { topPonProtectParamTemplateTable 1 }

		
		TopPonProtectParamTemplateEntry ::=
			SEQUENCE { 
				topPonProtectParamTemplateIndex
					INTEGER,
				topPonProtectParamBERThreshold
					INTEGER,
				topPonProtectParamBERRepeatTimes
					INTEGER,
				topPonProtectParamOpticalPowerUpperLimit
					INTEGER,
				topPonProtectParamOpticalPowerLowerLimit
					INTEGER,
				topPonProtectParamONUHandoverTime
					INTEGER,
				topPonProtectParamONULosSoakTime
					INTEGER,
				topPonProtectRestoreTime
					INTEGER,
				topPonProtectParamRowstatus
					RowStatus
			 }

		-- 1.3.6.1.4.1.32285.11.2.3.3.1.1.1.1
		topPonProtectParamTemplateIndex OBJECT-TYPE
			SYNTAX INTEGER
			MAX-ACCESS not-accessible
			STATUS current
			DESCRIPTION
				"template ID"
			::= { topPonProtectParamTemplateEntry 1 }

		
		-- 1.3.6.1.4.1.32285.11.2.3.3.1.1.1.2
		topPonProtectParamBERThreshold OBJECT-TYPE
			SYNTAX INTEGER
			MAX-ACCESS read-write
			STATUS current
			DESCRIPTION
				"BER threshold."
			::= { topPonProtectParamTemplateEntry 2 }

		
		-- 1.3.6.1.4.1.32285.11.2.3.3.1.1.1.3
		topPonProtectParamBERRepeatTimes OBJECT-TYPE
			SYNTAX INTEGER
			MAX-ACCESS read-create
			STATUS current
			DESCRIPTION
				"Times that BER is greater than threshold continueous.
				Over this value, system will cause auto switch.
				Default value is 1."
			::= { topPonProtectParamTemplateEntry 3 }

		
		-- 1.3.6.1.4.1.32285.11.2.3.3.1.1.1.4
		topPonProtectParamOpticalPowerUpperLimit OBJECT-TYPE
			SYNTAX INTEGER
			MAX-ACCESS read-create
			STATUS current
			DESCRIPTION
				"Too high optical signal will cause auto switch."
			::= { topPonProtectParamTemplateEntry 4 }

		
		-- 1.3.6.1.4.1.32285.11.2.3.3.1.1.1.5
		topPonProtectParamOpticalPowerLowerLimit OBJECT-TYPE
			SYNTAX INTEGER
			MAX-ACCESS read-create
			STATUS current
			DESCRIPTION
				"Too lower optical signal will cause auto switch."
			::= { topPonProtectParamTemplateEntry 5 }

		
		-- 1.3.6.1.4.1.32285.11.2.3.3.1.1.1.6
		topPonProtectParamONUHandoverTime OBJECT-TYPE
			SYNTAX INTEGER
			MAX-ACCESS read-create
			STATUS current
			DESCRIPTION
				"Handover time of ONU to switch.
				Default value is ."
			::= { topPonProtectParamTemplateEntry 6 }

		
		-- 1.3.6.1.4.1.32285.11.2.3.3.1.1.1.7
		topPonProtectParamONULosSoakTime OBJECT-TYPE
			SYNTAX INTEGER
			MAX-ACCESS read-create
			STATUS current
			DESCRIPTION
				"The interval time, ONU to send LOS signal.
				Default value is ."
			::= { topPonProtectParamTemplateEntry 7 }

		
		-- 1.3.6.1.4.1.32285.11.2.3.3.1.1.1.8
		topPonProtectRestoreTime OBJECT-TYPE
			SYNTAX INTEGER
			MAX-ACCESS read-create
			STATUS current
			DESCRIPTION
				"After this time, system will switch back automatically to 
				the previous work slot/pon, once the previous slot/pon 
				restores to normal condition, whatever reason 
				that system was switched (manual or auto).
				unit: seconds."
			DEFVAL { 30 }
			::= { topPonProtectParamTemplateEntry 8 }

		
		-- 1.3.6.1.4.1.32285.11.2.3.3.1.1.1.9
		topPonProtectParamRowstatus OBJECT-TYPE
			SYNTAX RowStatus
			MAX-ACCESS read-create
			STATUS current
			DESCRIPTION
				"Add/Del template"
			::= { topPonProtectParamTemplateEntry 9 }

		
		-- 1.3.6.1.4.1.32285.11.2.3.3.1.2
		topPonProtectConfigTable OBJECT-TYPE
			SYNTAX SEQUENCE OF TopPonProtectConfigEntry
			MAX-ACCESS not-accessible
			STATUS current
			DESCRIPTION
				"PON Protect table."
			::= { topPonProtectMgmtObjects 2 }

		
		-- 1.3.6.1.4.1.32285.11.2.3.3.1.2.1
		topPonProtectConfigEntry OBJECT-TYPE
			SYNTAX TopPonProtectConfigEntry
			MAX-ACCESS not-accessible
			STATUS current
			DESCRIPTION
				"Protect Group Index"
			INDEX { topPonProtectPGIndex }
			::= { topPonProtectConfigTable 1 }

		
		TopPonProtectConfigEntry ::=
			SEQUENCE { 
				topPonProtectPGIndex
					INTEGER,
				topPonProtectWorkSlot
					TopEPonSlotIndex,
				topPonProtectWorkPonPort
					TopEPonPonIndex,
				topPonProtectStandbySlot
					TopEPonSlotIndex,
				topPonProtectStandbyPonPort
					TopEPonPonIndex,
				topPonProtectSwitchCondition
					INTEGER,
				topPonProtectParamTemplate
					INTEGER,
				topPonProtectRTTMode
					INTEGER,
				topPonProtectDeltaRTT
					INTEGER,
				topPonProtectAdminStatus
					INTEGER,
				topPonProtectForceSwitch
					INTEGER,
				topPonProtectConfigRowStatus
					RowStatus
			 }

		-- 1.3.6.1.4.1.32285.11.2.3.3.1.2.1.1
		topPonProtectPGIndex OBJECT-TYPE
			SYNTAX INTEGER
			MAX-ACCESS not-accessible
			STATUS current
			DESCRIPTION
				"PON Protect Index."
			::= { topPonProtectConfigEntry 1 }

		
		-- 1.3.6.1.4.1.32285.11.2.3.3.1.2.1.2
		topPonProtectWorkSlot OBJECT-TYPE
			SYNTAX TopEPonSlotIndex
			MAX-ACCESS read-create
			STATUS current
			DESCRIPTION
				"Src Slot"
			::= { topPonProtectConfigEntry 2 }

		
		-- 1.3.6.1.4.1.32285.11.2.3.3.1.2.1.3
		topPonProtectWorkPonPort OBJECT-TYPE
			SYNTAX TopEPonPonIndex
			MAX-ACCESS read-create
			STATUS current
			DESCRIPTION
				"Pon index.
				(discard:SrcPort indicate one PON port, which is master.
				It is an Integer number, the lowest byte is pon index, then
				slot index, which use one byte.)"
			::= { topPonProtectConfigEntry 3 }

		
		-- 1.3.6.1.4.1.32285.11.2.3.3.1.2.1.4
		topPonProtectStandbySlot OBJECT-TYPE
			SYNTAX TopEPonSlotIndex
			MAX-ACCESS read-create
			STATUS current
			DESCRIPTION
				"slot index"
			::= { topPonProtectConfigEntry 4 }

		
		-- 1.3.6.1.4.1.32285.11.2.3.3.1.2.1.5
		topPonProtectStandbyPonPort OBJECT-TYPE
			SYNTAX TopEPonPonIndex
			MAX-ACCESS read-create
			STATUS current
			DESCRIPTION
				"PON index."
			::= { topPonProtectConfigEntry 5 }

		
		-- 1.3.6.1.4.1.32285.11.2.3.3.1.2.1.6
		topPonProtectSwitchCondition OBJECT-TYPE
			SYNTAX INTEGER
			MAX-ACCESS read-create
			STATUS current
			DESCRIPTION
				"It indicate the condition to cause auto switch, at the same time,
				bit7 show whether this PG allows to switch manually.
				From LSB, bit0-boarddOffline, bit1-LOS, bit2-Fatal(ex, power failure),
				bit3-OpticalHigh, bit4-OpticalLow, bit5-BERHigh.
				bit6-if set to 1, system will switch to previous working 
				slot/pon automatically once the previous slot/pon working normally
				for some time designated in variable topPonProtectRestoreTime.
				Moreover, the variables topPonProtectWorkSlot/topPonProtectWorkPonPort
				indicate the slot/pon, which system should switch to, after it has
				retore to work normally for topPonProtectRestoreTime seconds.
				bit7-manual switch enable(1)/disable(0)."
			::= { topPonProtectConfigEntry 6 }

		
		-- 1.3.6.1.4.1.32285.11.2.3.3.1.2.1.7
		topPonProtectParamTemplate OBJECT-TYPE
			SYNTAX INTEGER
			MAX-ACCESS read-create
			STATUS current
			DESCRIPTION
				"protect param template id."
			::= { topPonProtectConfigEntry 7 }

		
		-- 1.3.6.1.4.1.32285.11.2.3.3.1.2.1.8
		topPonProtectRTTMode OBJECT-TYPE
			SYNTAX INTEGER
				{
				static(1),
				dynamic(2)
				}
			MAX-ACCESS read-create
			STATUS current
			DESCRIPTION
				"Indicate the mode to obtain delta RTT between two links.
				Default value is static(1)."
			::= { topPonProtectConfigEntry 8 }

		
		-- 1.3.6.1.4.1.32285.11.2.3.3.1.2.1.9
		topPonProtectDeltaRTT OBJECT-TYPE
			SYNTAX INTEGER
			MAX-ACCESS read-create
			STATUS current
			DESCRIPTION
				"Indicate the delta RTT between two links. Default value is 0."
			::= { topPonProtectConfigEntry 9 }

		
		-- 1.3.6.1.4.1.32285.11.2.3.3.1.2.1.10
		topPonProtectAdminStatus OBJECT-TYPE
			SYNTAX INTEGER
				{
				enable(1),
				disable(2)
				}
			MAX-ACCESS read-create
			STATUS current
			DESCRIPTION
				"Enable/disable protect group."
			::= { topPonProtectConfigEntry 10 }

		
		-- 1.3.6.1.4.1.32285.11.2.3.3.1.2.1.11
		topPonProtectForceSwitch OBJECT-TYPE
			SYNTAX INTEGER
				{
				none(0),
				switch(1)
				}
			MAX-ACCESS read-create
			STATUS current
			DESCRIPTION
				"This command will make the current standby PON port start working,
				and make the current working PON port standby at the same time."
			::= { topPonProtectConfigEntry 11 }

		
		-- 1.3.6.1.4.1.32285.11.2.3.3.1.2.1.12
		topPonProtectConfigRowStatus OBJECT-TYPE
			SYNTAX RowStatus
			MAX-ACCESS read-create
			STATUS current
			DESCRIPTION
				"Add or Del protect group. Only createAndWait(5) and destroy(6) 
				are supported."
			::= { topPonProtectConfigEntry 12 }

		
		-- 1.3.6.1.4.1.32285.11.2.3.3.1.3
		topPonProtectStatusTable OBJECT-TYPE
			SYNTAX SEQUENCE OF TopPonProtectStatusEntry
			MAX-ACCESS not-accessible
			STATUS current
			DESCRIPTION
				"PON Protect table."
			::= { topPonProtectMgmtObjects 3 }

		
		-- 1.3.6.1.4.1.32285.11.2.3.3.1.3.1
		topPonProtectStatusEntry OBJECT-TYPE
			SYNTAX TopPonProtectStatusEntry
			MAX-ACCESS not-accessible
			STATUS current
			DESCRIPTION
				"Protect Group Index"
			INDEX { topPonProtectPGStatusIndex }
			::= { topPonProtectStatusTable 1 }

		
		TopPonProtectStatusEntry ::=
			SEQUENCE { 
				topPonProtectPGStatusIndex
					INTEGER,
				topPonProtectCurrentWorkSlot
					TopEPonSlotIndex,
				topPonProtectCurrentWorkPort
					TopEPonPonIndex,
				topPonProtectLastSwitchTime
					TimeStamp,
				topPonProtectLastSwitchReason
					INTEGER,
				topPonProtectLastSwitchResult
					INTEGER
			 }

		-- 1.3.6.1.4.1.32285.11.2.3.3.1.3.1.1
		topPonProtectPGStatusIndex OBJECT-TYPE
			SYNTAX INTEGER
			MAX-ACCESS not-accessible
			STATUS current
			DESCRIPTION
				"Actually, it is the PON protect group index in table topPonProtectConfigTable."
			::= { topPonProtectStatusEntry 1 }

		
		-- 1.3.6.1.4.1.32285.11.2.3.3.1.3.1.2
		topPonProtectCurrentWorkSlot OBJECT-TYPE
			SYNTAX TopEPonSlotIndex
			MAX-ACCESS read-only
			STATUS current
			DESCRIPTION
				"slot index"
			::= { topPonProtectStatusEntry 2 }

		
		-- 1.3.6.1.4.1.32285.11.2.3.3.1.3.1.3
		topPonProtectCurrentWorkPort OBJECT-TYPE
			SYNTAX TopEPonPonIndex
			MAX-ACCESS read-only
			STATUS current
			DESCRIPTION
				"pon index."
			::= { topPonProtectStatusEntry 3 }

		
		-- 1.3.6.1.4.1.32285.11.2.3.3.1.3.1.4
		topPonProtectLastSwitchTime OBJECT-TYPE
			SYNTAX TimeStamp
			MAX-ACCESS read-only
			STATUS current
			DESCRIPTION
				"Indicate timestamp of the last switch. Default value is 0(invalid)."
			::= { topPonProtectStatusEntry 4 }

		
		-- 1.3.6.1.4.1.32285.11.2.3.3.1.3.1.5
		topPonProtectLastSwitchReason OBJECT-TYPE
			SYNTAX INTEGER
				{
				invalid(0),
				manual(1),
				los(2),
				fatal(3),
				opticalPowerHigh(4),
				opticalPowerLow(5),
				berHigh(6)
				}
			MAX-ACCESS read-only
			STATUS current
			DESCRIPTION
				"Indicate the reason of the last switch. Default value is 0(invalid)."
			::= { topPonProtectStatusEntry 5 }

		
		-- 1.3.6.1.4.1.32285.11.2.3.3.1.3.1.6
		topPonProtectLastSwitchResult OBJECT-TYPE
			SYNTAX INTEGER
				{
				invalid(0),
				success(1),
				failure(2)
				}
			MAX-ACCESS read-only
			STATUS current
			DESCRIPTION
				"Indicate the switch result of the last time. Default value is 0(invalid)."
			::= { topPonProtectStatusEntry 6 }

		
		-- 1.3.6.1.4.1.32285.11.2.3.3.2
		topAclMgmtObjects OBJECT IDENTIFIER ::= { topPonPortObjects 2 }

		
		-- 1.3.6.1.4.1.32285.11.2.3.3.2.1
		topPortACLListTable OBJECT-TYPE
			SYNTAX SEQUENCE OF TopPortACLListEntry
			MAX-ACCESS not-accessible
			STATUS current
			DESCRIPTION
				"ACL table applies on OLT pon port, OLT SNI, OLT onu ID, ONU UNI.
				for the purpose of ACL and QinQ feature."
			::= { topAclMgmtObjects 1 }

		
		-- 1.3.6.1.4.1.32285.11.2.3.3.2.1.1
		topPortACLListEntry OBJECT-TYPE
			SYNTAX TopPortACLListEntry
			MAX-ACCESS not-accessible
			STATUS current
			DESCRIPTION
				"Port include PON/SNI/UNI."
			INDEX { topAclDeviceIndex, topPortAclListIndex, topAclPortDirection }
			::= { topPortACLListTable 1 }

		
		TopPortACLListEntry ::=
			SEQUENCE { 
				topAclDeviceIndex
					EponDeviceIndex,
				topPortAclListIndex
					INTEGER,
				topAclPortDirection
					INTEGER,
				topAclRowStatus
					RowStatus
			 }

		-- 1.3.6.1.4.1.32285.11.2.3.3.2.1.1.1
		topAclDeviceIndex OBJECT-TYPE
			SYNTAX EponDeviceIndex
			MAX-ACCESS not-accessible
			STATUS current
			DESCRIPTION
				"From MSB on, SLOT index, PON/SNI index, ONU auth index,
				and uni port index.
				For PON/SNI, ONU auth and uni reserved 0."
			::= { topPortACLListEntry 1 }

		
		-- 1.3.6.1.4.1.32285.11.2.3.3.2.1.1.2
		topPortAclListIndex OBJECT-TYPE
			SYNTAX INTEGER
			MAX-ACCESS not-accessible
			STATUS current
			DESCRIPTION
				"ACL RuleList Index"
			::= { topPortACLListEntry 2 }

		
		-- 1.3.6.1.4.1.32285.11.2.3.3.2.1.1.3
		topAclPortDirection OBJECT-TYPE
			SYNTAX INTEGER
				{
				ingress(0),
				egress(1)
				}
			MAX-ACCESS not-accessible
			STATUS current
			DESCRIPTION
				"direction"
			::= { topPortACLListEntry 3 }

		
		-- 1.3.6.1.4.1.32285.11.2.3.3.2.1.1.4
		topAclRowStatus OBJECT-TYPE
			SYNTAX RowStatus
			MAX-ACCESS read-create
			STATUS current
			DESCRIPTION
				"Add/Del/Set"
			::= { topPortACLListEntry 4 }

		
		-- 1.3.6.1.4.1.32285.11.2.3.3.2.2
		topAclListTable OBJECT-TYPE
			SYNTAX SEQUENCE OF TopAclListEntry
			MAX-ACCESS not-accessible
			STATUS current
			DESCRIPTION
				"ACL list table"
			::= { topAclMgmtObjects 2 }

		
		-- 1.3.6.1.4.1.32285.11.2.3.3.2.2.1
		topAclListEntry OBJECT-TYPE
			SYNTAX TopAclListEntry
			MAX-ACCESS not-accessible
			STATUS current
			DESCRIPTION
				"ACL list entry"
			INDEX { topAclListIndex }
			::= { topAclListTable 1 }

		
		TopAclListEntry ::=
			SEQUENCE { 
				topAclListIndex
					INTEGER,
				topAclDescription
					DisplayString,
				topAclRuleNum
					INTEGER,
				topAclRulePriority
					INTEGER,
				topRuleRowStatus
					RowStatus
			 }

		-- 1.3.6.1.4.1.32285.11.2.3.3.2.2.1.1
		topAclListIndex OBJECT-TYPE
			SYNTAX INTEGER
			MAX-ACCESS not-accessible
			STATUS current
			DESCRIPTION
				"ACL List Index"
			::= { topAclListEntry 1 }

		
		-- 1.3.6.1.4.1.32285.11.2.3.3.2.2.1.2
		topAclDescription OBJECT-TYPE
			SYNTAX DisplayString (SIZE (1..63))
			MAX-ACCESS read-create
			STATUS current
			DESCRIPTION
				"ACL Description"
			DEFVAL { "ACL_1" }
			::= { topAclListEntry 2 }

		
		-- 1.3.6.1.4.1.32285.11.2.3.3.2.2.1.3
		topAclRuleNum OBJECT-TYPE
			SYNTAX INTEGER (0..16)
			MAX-ACCESS read-only
			STATUS current
			DESCRIPTION
				"ACL rule quantity."
			::= { topAclListEntry 3 }

		
		-- 1.3.6.1.4.1.32285.11.2.3.3.2.2.1.4
		topAclRulePriority OBJECT-TYPE
			SYNTAX INTEGER (1..16)
			MAX-ACCESS read-create
			STATUS current
			DESCRIPTION
				"priority of ACL list index"
			DEFVAL { 1 }
			::= { topAclListEntry 4 }

		
		-- 1.3.6.1.4.1.32285.11.2.3.3.2.2.1.5
		topRuleRowStatus OBJECT-TYPE
			SYNTAX RowStatus
			MAX-ACCESS read-create
			STATUS current
			DESCRIPTION
				"Add/Del/Set"
			::= { topAclListEntry 5 }

		
		-- 1.3.6.1.4.1.32285.11.2.3.3.2.3
		topAclRuleTable OBJECT-TYPE
			SYNTAX SEQUENCE OF TopAclRuleEntry
			MAX-ACCESS not-accessible
			STATUS current
			DESCRIPTION
				"ACL rule table"
			::= { topAclMgmtObjects 3 }

		
		-- 1.3.6.1.4.1.32285.11.2.3.3.2.3.1
		topAclRuleEntry OBJECT-TYPE
			SYNTAX TopAclRuleEntry
			MAX-ACCESS not-accessible
			STATUS current
			DESCRIPTION
				"ACL rule entry"
			INDEX { topAclRuleListIndex, topAclRuleIndex }
			::= { topAclRuleTable 1 }

		
		TopAclRuleEntry ::=
			SEQUENCE { 
				topAclRuleListIndex
					INTEGER,
				topAclRuleIndex
					INTEGER,
				topMatchedFieldSelection
					BITS,
				topMatchedSrcMac
					MacAddress,
				topMatchedSrcMacMask
					MacAddress,
				topMatchedDstMac
					MacAddress,
				topMatchedDstMacMask
					MacAddress,
				topMatchedStartSVid
					INTEGER,
				topMatchedEndSVid
					INTEGER,
				topMatchedStartCVid
					INTEGER,
				topMatchedEndCVid
					INTEGER,
				topMatchedOuterCos
					INTEGER,
				topMatchedInnerCos
					INTEGER,
				topMatchedOuterTpid
					INTEGER,
				topMatchedInnerTpid
					INTEGER,
				topMatchedEthernetType
					INTEGER,
				topMatchedSrcIP
					IpAddress,
				topMatchedSrcIPMask
					IpAddress,
				topMatchedDstIP
					IpAddress,
				topMatchedDstIPMask
					IpAddress,
				topMatchedL3ProtocolClass
					INTEGER,
				topMatchedIpProtocol
					INTEGER,
				topMatchedDscp
					INTEGER,
				topMatchedTos
					INTEGER,
				topMatchedStartSrcPort
					INTEGER,
				topMatchedEndSrcPort
					INTEGER,
				topMatchedStartDstPort
					INTEGER,
				topMatchedEndDstPort
					INTEGER,
				topAclAction
					BITS,
				topAclActionParameter
					OCTET STRING,
				topAclRuleRowStatus
					RowStatus
			 }

		-- 1.3.6.1.4.1.32285.11.2.3.3.2.3.1.1
		topAclRuleListIndex OBJECT-TYPE
			SYNTAX INTEGER
			MAX-ACCESS not-accessible
			STATUS current
			DESCRIPTION
				"ACL RuleList Index"
			::= { topAclRuleEntry 1 }

		
		-- 1.3.6.1.4.1.32285.11.2.3.3.2.3.1.2
		topAclRuleIndex OBJECT-TYPE
			SYNTAX INTEGER (1..16)
			MAX-ACCESS not-accessible
			STATUS current
			DESCRIPTION
				"ACL Rule Index, also index is rule priority."
			::= { topAclRuleEntry 2 }

		
		-- 1.3.6.1.4.1.32285.11.2.3.3.2.3.1.3
		topMatchedFieldSelection OBJECT-TYPE
			SYNTAX BITS
				{
				srcMac(0),
				dstMac(1),
				outerVid(2),
				innerVid(3),
				outerCos(4),
				innerCos(5),
				outerTpid(6),
				innerTpid(7),
				ethernetType(8),
				srcIp(9),
				dstIp(10),
				ipProtocolClass(11),
				ipProtocolType(12),
				dscp(13),
				tos(14),
				srcPort(15),
				dstPort(16),
				reserved1(17),
				reserved2(18),
				reserved3(19),
				reserved4(20),
				reserved5(21),
				reserved6(22),
				reserved7(23),
				reserved8(24),
				reserved9(25),
				reserved10(26)
				}
			MAX-ACCESS read-create
			STATUS current
			DESCRIPTION
				"match field"
			::= { topAclRuleEntry 3 }

		
		-- 1.3.6.1.4.1.32285.11.2.3.3.2.3.1.4
		topMatchedSrcMac OBJECT-TYPE
			SYNTAX MacAddress
			MAX-ACCESS read-create
			STATUS current
			DESCRIPTION
				"source MAC address"
			::= { topAclRuleEntry 4 }

		
		-- 1.3.6.1.4.1.32285.11.2.3.3.2.3.1.5
		topMatchedSrcMacMask OBJECT-TYPE
			SYNTAX MacAddress
			MAX-ACCESS read-create
			STATUS current
			DESCRIPTION
				"source MAC mask"
			::= { topAclRuleEntry 5 }

		
		-- 1.3.6.1.4.1.32285.11.2.3.3.2.3.1.6
		topMatchedDstMac OBJECT-TYPE
			SYNTAX MacAddress
			MAX-ACCESS read-create
			STATUS current
			DESCRIPTION
				"destination MAC address"
			::= { topAclRuleEntry 6 }

		
		-- 1.3.6.1.4.1.32285.11.2.3.3.2.3.1.7
		topMatchedDstMacMask OBJECT-TYPE
			SYNTAX MacAddress
			MAX-ACCESS read-create
			STATUS current
			DESCRIPTION
				"destination MAC mask"
			::= { topAclRuleEntry 7 }

		
		-- 1.3.6.1.4.1.32285.11.2.3.3.2.3.1.8
		topMatchedStartSVid OBJECT-TYPE
			SYNTAX INTEGER (1..4094)
			MAX-ACCESS read-create
			STATUS current
			DESCRIPTION
				"min value of svlan id range"
			::= { topAclRuleEntry 8 }

		
		-- 1.3.6.1.4.1.32285.11.2.3.3.2.3.1.9
		topMatchedEndSVid OBJECT-TYPE
			SYNTAX INTEGER (1..4094)
			MAX-ACCESS read-create
			STATUS current
			DESCRIPTION
				"max value of svlan id range"
			::= { topAclRuleEntry 9 }

		
		-- 1.3.6.1.4.1.32285.11.2.3.3.2.3.1.10
		topMatchedStartCVid OBJECT-TYPE
			SYNTAX INTEGER (1..4094)
			MAX-ACCESS read-create
			STATUS current
			DESCRIPTION
				"min value of cvlan id range"
			::= { topAclRuleEntry 10 }

		
		-- 1.3.6.1.4.1.32285.11.2.3.3.2.3.1.11
		topMatchedEndCVid OBJECT-TYPE
			SYNTAX INTEGER (1..4094)
			MAX-ACCESS read-create
			STATUS current
			DESCRIPTION
				"max value of cvlan id range"
			::= { topAclRuleEntry 11 }

		
		-- 1.3.6.1.4.1.32285.11.2.3.3.2.3.1.12
		topMatchedOuterCos OBJECT-TYPE
			SYNTAX INTEGER (0..7)
			MAX-ACCESS read-create
			STATUS current
			DESCRIPTION
				"outer cos priority"
			::= { topAclRuleEntry 12 }

		
		-- 1.3.6.1.4.1.32285.11.2.3.3.2.3.1.13
		topMatchedInnerCos OBJECT-TYPE
			SYNTAX INTEGER (0..7)
			MAX-ACCESS read-create
			STATUS current
			DESCRIPTION
				"inner cos priority"
			::= { topAclRuleEntry 13 }

		
		-- 1.3.6.1.4.1.32285.11.2.3.3.2.3.1.14
		topMatchedOuterTpid OBJECT-TYPE
			SYNTAX INTEGER (1..65535)
			MAX-ACCESS read-create
			STATUS current
			DESCRIPTION
				"outer tpid"
			::= { topAclRuleEntry 14 }

		
		-- 1.3.6.1.4.1.32285.11.2.3.3.2.3.1.15
		topMatchedInnerTpid OBJECT-TYPE
			SYNTAX INTEGER (1..65535)
			MAX-ACCESS read-create
			STATUS current
			DESCRIPTION
				"inner tpid"
			::= { topAclRuleEntry 15 }

		
		-- 1.3.6.1.4.1.32285.11.2.3.3.2.3.1.16
		topMatchedEthernetType OBJECT-TYPE
			SYNTAX INTEGER (1..65535)
			MAX-ACCESS read-create
			STATUS current
			DESCRIPTION
				"It is presented in decimal value for heximal EtherType"
			::= { topAclRuleEntry 16 }

		
		-- 1.3.6.1.4.1.32285.11.2.3.3.2.3.1.17
		topMatchedSrcIP OBJECT-TYPE
			SYNTAX IpAddress
			MAX-ACCESS read-create
			STATUS current
			DESCRIPTION
				"Source IP"
			::= { topAclRuleEntry 17 }

		
		-- 1.3.6.1.4.1.32285.11.2.3.3.2.3.1.18
		topMatchedSrcIPMask OBJECT-TYPE
			SYNTAX IpAddress
			MAX-ACCESS read-create
			STATUS current
			DESCRIPTION
				"Source IP Mask"
			::= { topAclRuleEntry 18 }

		
		-- 1.3.6.1.4.1.32285.11.2.3.3.2.3.1.19
		topMatchedDstIP OBJECT-TYPE
			SYNTAX IpAddress
			MAX-ACCESS read-create
			STATUS current
			DESCRIPTION
				"Destination IP"
			::= { topAclRuleEntry 19 }

		
		-- 1.3.6.1.4.1.32285.11.2.3.3.2.3.1.20
		topMatchedDstIPMask OBJECT-TYPE
			SYNTAX IpAddress
			MAX-ACCESS read-create
			STATUS current
			DESCRIPTION
				"Destination IP Mask"
			::= { topAclRuleEntry 20 }

		
		-- 1.3.6.1.4.1.32285.11.2.3.3.2.3.1.21
		topMatchedL3ProtocolClass OBJECT-TYPE
			SYNTAX INTEGER
				{
				nonIp(1),
				nonIpv4(2),
				ipv4(3),
				nonIpv6(4),
				ipv6(5)
				}
			MAX-ACCESS read-create
			STATUS current
			DESCRIPTION
				"ip protocol class, include non-ip,
				non-ipv4,ipv4,non-ipv6,ipv6.
				non-ip: any protocol except for ip.
				nonIpv4: any protocol excpet for ipv4.
				ipv4: ipv4 only.
				ipv6: ipv6 only.
				nonIpv6: any protocol except for ipv6.
				"
			::= { topAclRuleEntry 21 }

		
		-- 1.3.6.1.4.1.32285.11.2.3.3.2.3.1.22
		topMatchedIpProtocol OBJECT-TYPE
			SYNTAX INTEGER (0..255)
			MAX-ACCESS read-create
			STATUS current
			DESCRIPTION
				"IP protocol type, including icmp,igmp, tcp, egp, udp."
			::= { topAclRuleEntry 22 }

		
		-- 1.3.6.1.4.1.32285.11.2.3.3.2.3.1.23
		topMatchedDscp OBJECT-TYPE
			SYNTAX INTEGER (0..63)
			MAX-ACCESS read-create
			STATUS current
			DESCRIPTION
				"dscp"
			::= { topAclRuleEntry 23 }

		
		-- 1.3.6.1.4.1.32285.11.2.3.3.2.3.1.24
		topMatchedTos OBJECT-TYPE
			SYNTAX INTEGER (0..7)
			MAX-ACCESS read-create
			STATUS current
			DESCRIPTION
				"dscp"
			::= { topAclRuleEntry 24 }

		
		-- 1.3.6.1.4.1.32285.11.2.3.3.2.3.1.25
		topMatchedStartSrcPort OBJECT-TYPE
			SYNTAX INTEGER (0..65535)
			MAX-ACCESS read-create
			STATUS current
			DESCRIPTION
				"Min value of L4 source port"
			::= { topAclRuleEntry 25 }

		
		-- 1.3.6.1.4.1.32285.11.2.3.3.2.3.1.26
		topMatchedEndSrcPort OBJECT-TYPE
			SYNTAX INTEGER (0..65535)
			MAX-ACCESS read-create
			STATUS current
			DESCRIPTION
				"Max value of L4 source port"
			::= { topAclRuleEntry 26 }

		
		-- 1.3.6.1.4.1.32285.11.2.3.3.2.3.1.27
		topMatchedStartDstPort OBJECT-TYPE
			SYNTAX INTEGER (0..65535)
			MAX-ACCESS read-create
			STATUS current
			DESCRIPTION
				"Min value of L4 destination port"
			::= { topAclRuleEntry 27 }

		
		-- 1.3.6.1.4.1.32285.11.2.3.3.2.3.1.28
		topMatchedEndDstPort OBJECT-TYPE
			SYNTAX INTEGER (0..65535)
			MAX-ACCESS read-create
			STATUS current
			DESCRIPTION
				"Max value of L4 destination port"
			::= { topAclRuleEntry 28 }

		
		-- 1.3.6.1.4.1.32285.11.2.3.3.2.3.1.29
		topAclAction OBJECT-TYPE
			SYNTAX BITS
				{
				permitDenyMode(0),
				permitDenyValue(1),
				setIngressRate(2),
				mirror(3),
				setQueue(4),
				markInnerCos(5),
				markDscp(6),
				markTos(7),
				addOuterVlan(8),
				scosMode(9),
				tpidMode(10),
				copyToCpu(11),
				reserved2(12),
				reserved3(13),
				reserved4(14),
				reserved5(15)
				}
			MAX-ACCESS read-create
			STATUS current
			DESCRIPTION
				"two OCTETs:
				note:
				the following coding rule diffrent from ASN.1,
				but BITS will follow ASN.1 still.
                ------------------
				OCTET1:
				BIT0: 1-permitdeny mode, 
				      0-other mode, including setIngressRate, setQueue, 
				        mirror,makrCos, markdscp, marktos, addoutervlan
				BIT1: 1-permit; 0-deny;
				BIT2: 1-set ingress rate limit; 0-not limited; unit: kbps
				BIT3: 1-mirror to other port; 0-not mirror;
				BIT4: 1-set to some specific queue; 0-default queue;
				BIT5: 1-mark inner cos; 0-keep the current inner cos value
				BIT6: 1-mark DSCP; 0-keep the current DSCP value
				BIT7: 1-mark tos; 0-keep the current TOS value
                -------------------
				OCTET2:
				BIT8: 1-add svlan; 0-keep the current vlan stacking
				BIT9: 0-copy ccos to scos, valid only BIT8=1;
				      1-use a specific cos value from topAclActionParameter,
				        vlaid only BIT8=1.
				BIT10:0-copy tpid from inner tpid, valid only BIT8=1;
				      1-use a specific tpid value from topAclActionParameter,
				        vlaid only BIT8=1.
                BIT11:1-copy data to cpu,0-default.
				    BIT12:reserved 0
				    BIT13:reserved 0
				    BIT14:reserved 0
				    BIT15:reserved 0
				"
			::= { topAclRuleEntry 29 }

		
		-- 1.3.6.1.4.1.32285.11.2.3.3.2.3.1.30
		topAclActionParameter OBJECT-TYPE
			SYNTAX OCTET STRING (SIZE (15))
			MAX-ACCESS read-create
			STATUS current
			DESCRIPTION
				"ACL action parameter description:
				this variable is valid only when topAclAction is not permit/deny.
				from MSB on,
				OCTET1-2(2 bytes): ingress rate limit
				OCTET3-6(4 bytes): format is SLOT-PON/SNI-ONUAUTH-UNI
				    for PON/SNI, OUNAUTH and UNI set to 0x00
				OCTET7(1 byte): queue id
				OCTET8(1 byte): inner CoS
				OCTET9(1 byte): DSCP
				OCTET10(1 byte): TOS
				OCTET11-12: SVLAN ID
				OCTET13: SCOS, default value is 0
				OCTET14-15: outer TPID, defaut value is 0x8100
				Furthermore, for each OCTET, should be filled with 0x00 
				in case the specific field is invalid."
			::= { topAclRuleEntry 30 }

		
		-- 1.3.6.1.4.1.32285.11.2.3.3.2.3.1.31
		topAclRuleRowStatus OBJECT-TYPE
			SYNTAX RowStatus
			MAX-ACCESS read-create
			STATUS current
			DESCRIPTION
				"Add/Del/Set"
			::= { topAclRuleEntry 31 }


		-- 1.3.6.1.4.1.32285.11.2.3.3.3
		topPonOnuAuthModeTable OBJECT-TYPE
			SYNTAX SEQUENCE OF TopPonOnuAuthModeEntry
			MAX-ACCESS not-accessible
			STATUS current
			DESCRIPTION
				"ONU auth policy based on pon port"
			::= { topPonPortObjects 3 }

		
		-- 1.3.6.1.4.1.32285.11.2.3.3.3.1
		topPonOnuAuthModeEntry OBJECT-TYPE
			SYNTAX TopPonOnuAuthModeEntry
			MAX-ACCESS not-accessible
			STATUS current
			DESCRIPTION
				"ONU auth mode"
			INDEX { topPonOnuAuthModeCardIndex, topPonOnuAuthModePonIndex }
			::= { topPonOnuAuthModeTable 1 }

		
		TopPonOnuAuthModeEntry ::=
			SEQUENCE { 
				topPonOnuAuthModeCardIndex
					TopEPonSlotIndex,
				topPonOnuAuthModePonIndex
					TopEPonPonIndex,
				topPonOnuAuthModeMode
					INTEGER
			 }

		-- 1.3.6.1.4.1.32285.11.2.3.3.3.1.1
		topPonOnuAuthModeCardIndex OBJECT-TYPE
			SYNTAX TopEPonSlotIndex
			MAX-ACCESS not-accessible
			STATUS current
			DESCRIPTION
				"slot index"
			::= { topPonOnuAuthModeEntry 1 }

		
		-- 1.3.6.1.4.1.32285.11.2.3.3.3.1.2
		topPonOnuAuthModePonIndex OBJECT-TYPE
			SYNTAX TopEPonPonIndex
			MAX-ACCESS not-accessible
			STATUS current
			DESCRIPTION
				"Pon index"
			::= { topPonOnuAuthModeEntry 2 }

		
		-- 1.3.6.1.4.1.32285.11.2.3.3.3.1.3
		topPonOnuAuthModeMode OBJECT-TYPE
			SYNTAX INTEGER (2..4)
			MAX-ACCESS read-write
			STATUS current
			DESCRIPTION
				"Onu auth policy based on pon port.
				This table will not support rowstatus, it's a static table, created automatically as per epua board.
				TK_MAC_AUTH = 0x2 
				TK_MIX_AUTH = 0x3, 
				TK_LOID_AUTH= 0x4"
			DEFVAL { 3 }
			::= { topPonOnuAuthModeEntry 3 }

		
		-- 1.3.6.1.4.1.32285.11.2.3.3.4
		topPonOnuAutoAuthModeTable OBJECT-TYPE
			SYNTAX SEQUENCE OF TopPonOnuAutoAuthModeEntry
			MAX-ACCESS not-accessible
			STATUS current
			DESCRIPTION
				"Onu Auto Auth Mode Table."
			::= { topPonPortObjects 4 }

		
		-- 1.3.6.1.4.1.32285.11.2.3.3.4.1
		topPonOnuAutoAuthModeEntry OBJECT-TYPE
			SYNTAX TopPonOnuAutoAuthModeEntry
			MAX-ACCESS not-accessible
			STATUS current
			DESCRIPTION
				"Onu Auto Auth Mode Entry."
			INDEX { topPonOnuAutoAuthModeCardIndex, topPonOnuAutoAuthModePonIndex }
			::= { topPonOnuAutoAuthModeTable 1 }

		
		TopPonOnuAutoAuthModeEntry ::=
			SEQUENCE { 
				topPonOnuAutoAuthModeCardIndex
					TopEPonSlotIndex,
				topPonOnuAutoAuthModePonIndex
					TopEPonPonIndex,
				topPonOnuAutoAuthEnable
					INTEGER
			 }

		-- 1.3.6.1.4.1.32285.11.2.3.3.4.1.1
		topPonOnuAutoAuthModeCardIndex OBJECT-TYPE
			SYNTAX TopEPonSlotIndex
			MAX-ACCESS not-accessible
			STATUS current
			DESCRIPTION
				"Slot index."
			::= { topPonOnuAutoAuthModeEntry 1 }

		
		-- 1.3.6.1.4.1.32285.11.2.3.3.4.1.2
		topPonOnuAutoAuthModePonIndex OBJECT-TYPE
			SYNTAX TopEPonPonIndex
			MAX-ACCESS not-accessible
			STATUS current
			DESCRIPTION
				"Pon index."
			::= { topPonOnuAutoAuthModeEntry 2 }

		
		-- 1.3.6.1.4.1.32285.11.2.3.3.4.1.3
		topPonOnuAutoAuthEnable OBJECT-TYPE
			SYNTAX INTEGER
				{
				disable(0),
				enable(1)
				}
			MAX-ACCESS read-write
			STATUS current
			DESCRIPTION
				"ONU atuo authentication configuration."
			DEFVAL { 0 }
			::= { topPonOnuAutoAuthModeEntry 3 }
			
			
		-- 1.3.6.1.4.1.32285.11.2.3.4
		topOnuObjects OBJECT IDENTIFIER ::= { topvisionEponTree 4 }

		
		-- 1.3.6.1.4.1.32285.11.2.3.4.1
		topOnuCapabilityTable OBJECT-TYPE
			SYNTAX SEQUENCE OF TopOnuCapabilityEntry
			MAX-ACCESS not-accessible
			STATUS current
			DESCRIPTION
				"A list of onuCapTable entries. "
			::= { topOnuObjects 1 }

		
		-- 1.3.6.1.4.1.32285.11.2.3.4.1.1
		topOnuCapabilityEntry OBJECT-TYPE
			SYNTAX TopOnuCapabilityEntry
			MAX-ACCESS not-accessible
			STATUS current
			DESCRIPTION
				"The topOnuCapabilityEntry Information"
			INDEX { topOnuCapCardIndex, topOnuCapPonIndex, topOnuCapOnuIndex }
			::= { topOnuCapabilityTable 1 }

		
		TopOnuCapabilityEntry ::=
			SEQUENCE { 
				topOnuCapCardIndex
					TopEPonSlotIndex,
				topOnuCapPonIndex
					TopEPonPonIndex,
				topOnuCapOnuIndex
					TopEPonOnuAuthNum,
				topOnuCapDeregister
					INTEGER,
				topOnuCapMacAddrMaxQuantity
					INTEGER,
				topOnuPonPerfStats15minuteEnable
					INTEGER,
				topOnuPonPerfStats24hourEnable
					INTEGER,
				topOnuTemperatureDetectEnable
					INTEGER,
				topOnuCurrentTemperature
					INTEGER,
				topOnuIsolationEnable
					INTEGER
			 }

		-- 1.3.6.1.4.1.32285.11.2.3.4.1.1.1
		topOnuCapCardIndex OBJECT-TYPE
			SYNTAX TopEPonSlotIndex
			MAX-ACCESS not-accessible
			STATUS current
			DESCRIPTION
				"onu slot Index"
			::= { topOnuCapabilityEntry 1 }

		
		-- 1.3.6.1.4.1.32285.11.2.3.4.1.1.2
		topOnuCapPonIndex OBJECT-TYPE
			SYNTAX TopEPonPonIndex
			MAX-ACCESS not-accessible
			STATUS current
			DESCRIPTION
				"onu pon Index"
			::= { topOnuCapabilityEntry 2 }

		
		-- 1.3.6.1.4.1.32285.11.2.3.4.1.1.3
		topOnuCapOnuIndex OBJECT-TYPE
			SYNTAX TopEPonOnuAuthNum
			MAX-ACCESS not-accessible
			STATUS current
			DESCRIPTION
				"onu auth Index"
			::= { topOnuCapabilityEntry 3 }

		
		-- 1.3.6.1.4.1.32285.11.2.3.4.1.1.4
		topOnuCapDeregister OBJECT-TYPE
			SYNTAX INTEGER
				{
				noOperation(0),
				deregister(1)
				}
			MAX-ACCESS read-write
			STATUS current
			DESCRIPTION
				"deregister ONU"
			DEFVAL { 0 }
			::= { topOnuCapabilityEntry 4 }

		
		-- 1.3.6.1.4.1.32285.11.2.3.4.1.1.5
		topOnuCapMacAddrMaxQuantity OBJECT-TYPE
			SYNTAX INTEGER (0..64)
			MAX-ACCESS read-write
			STATUS current
			DESCRIPTION
				"total mac add capability in ONU
				0:do not limit, max value depend on ONU
				other value: limited to specfic value"
			::= { topOnuCapabilityEntry 5 }

		
		-- 1.3.6.1.4.1.32285.11.2.3.4.1.1.6
		topOnuPonPerfStats15minuteEnable OBJECT-TYPE
			SYNTAX INTEGER
				{
				enable(1),
				disable(2)
				}
			MAX-ACCESS read-write
			STATUS current
			DESCRIPTION
				"disable-2, enable-1"
			DEFVAL { 2 }
			::= { topOnuCapabilityEntry 6 }

		
		-- 1.3.6.1.4.1.32285.11.2.3.4.1.1.7
		topOnuPonPerfStats24hourEnable OBJECT-TYPE
			SYNTAX INTEGER
				{
				enable(1),
				disable(2)
				}
			MAX-ACCESS read-write
			STATUS current
			DESCRIPTION
				"disable-2, enable-1"
			DEFVAL { 2 }
			::= { topOnuCapabilityEntry 7 }

		
		-- 1.3.6.1.4.1.32285.11.2.3.4.1.1.8
		topOnuTemperatureDetectEnable OBJECT-TYPE
			SYNTAX INTEGER
				{
				enable(1),
				disable(2)
				}
			MAX-ACCESS read-write
			STATUS current
			DESCRIPTION
				"disable-2, enable-1"
			DEFVAL { 2 }
			::= { topOnuCapabilityEntry 8 }

		
		-- 1.3.6.1.4.1.32285.11.2.3.4.1.1.9
		topOnuCurrentTemperature OBJECT-TYPE
			SYNTAX INTEGER
			MAX-ACCESS read-only
			STATUS current
			DESCRIPTION
				"when ONU does not support temperature detection,
				fill with the temperature of optical module in PON port."
			::= { topOnuCapabilityEntry 9 }

		
		-- 1.3.6.1.4.1.32285.11.2.3.4.1.1.10
		topOnuIsolationEnable OBJECT-TYPE
			SYNTAX INTEGER
				{
				true(1),
				false(2)
				}
			MAX-ACCESS read-write
			STATUS current
			DESCRIPTION
				"Description."
			::= { topOnuCapabilityEntry 10 }
			
		-- 1.3.6.1.4.1.32285.11.2.3.4.2
		topOnuAuthMgmt OBJECT IDENTIFIER ::= { topOnuObjects 2 }

		
		-- 1.3.6.1.4.1.32285.11.2.3.4.2.1
		topOnuAuthLogicSnTable OBJECT-TYPE
			SYNTAX SEQUENCE OF TopOnuAuthLogicSNEntry
			MAX-ACCESS not-accessible
			STATUS current
			DESCRIPTION
				"A list of onuAuthenticationPreConfigTable entries. "
			::= { topOnuAuthMgmt 1 }

		
		-- 1.3.6.1.4.1.32285.11.2.3.4.2.1.1
		topOnuAuthLogicSnEntry OBJECT-TYPE
			SYNTAX TopOnuAuthLogicSNEntry
			MAX-ACCESS not-accessible
			STATUS current
			DESCRIPTION
				"The onuAuthenticationPreConfigEntry Information"
			INDEX { topOnuAuthLogicSnCardIndex, topOnuAuthLogicSnPonIndex, topOnuAuthLogicSnOnuIndex }
			::= { topOnuAuthLogicSnTable 1 }

		
		TopOnuAuthLogicSNEntry ::=
			SEQUENCE { 
				topOnuAuthLogicSnCardIndex
					TopEPonSlotIndex,
				topOnuAuthLogicSnPonIndex
					TopEPonPonIndex,
				topOnuAuthLogicSnOnuIndex
					TopEPonOnuAuthNum,
				topOnuAuthLogicSnMode
					INTEGER,
				topOnuAuthLogicSn
					OCTET STRING,
				topOnuAuthPassword
					OCTET STRING,
				topOnuAuthLogicSnAction
					INTEGER,
				topOnuAuthLogicSnRowStatus
					RowStatus
			 }

		-- 1.3.6.1.4.1.32285.11.2.3.4.2.1.1.1
		topOnuAuthLogicSnCardIndex OBJECT-TYPE
			SYNTAX TopEPonSlotIndex
			MAX-ACCESS not-accessible
			STATUS current
			DESCRIPTION
				"slot Index"
			::= { topOnuAuthLogicSnEntry 1 }

		
		-- 1.3.6.1.4.1.32285.11.2.3.4.2.1.1.2
		topOnuAuthLogicSnPonIndex OBJECT-TYPE
			SYNTAX TopEPonPonIndex
			MAX-ACCESS not-accessible
			STATUS current
			DESCRIPTION
				"pon Index"
			::= { topOnuAuthLogicSnEntry 2 }

		
		-- 1.3.6.1.4.1.32285.11.2.3.4.2.1.1.3
		topOnuAuthLogicSnOnuIndex OBJECT-TYPE
			SYNTAX TopEPonOnuAuthNum
			MAX-ACCESS not-accessible
			STATUS current
			DESCRIPTION
				"onu logical ID"
			::= { topOnuAuthLogicSnEntry 3 }

		
		-- 1.3.6.1.4.1.32285.11.2.3.4.2.1.1.4
		topOnuAuthLogicSnMode OBJECT-TYPE
			SYNTAX INTEGER
				{
				logicSnAndPassword(1),
				logicSnOnly(2)
				}
			MAX-ACCESS read-create
			STATUS current
			DESCRIPTION
				"1-logic sn+password,
				2-logic sn only"
			DEFVAL { 1 }
			::= { topOnuAuthLogicSnEntry 4 }

		
		-- 1.3.6.1.4.1.32285.11.2.3.4.2.1.1.5
		topOnuAuthLogicSn OBJECT-TYPE
			SYNTAX OCTET STRING (SIZE (1..24))
			MAX-ACCESS read-create
			STATUS current
			DESCRIPTION
				"logic sn"
			::= { topOnuAuthLogicSnEntry 5 }

		
		-- 1.3.6.1.4.1.32285.11.2.3.4.2.1.1.6
		topOnuAuthPassword OBJECT-TYPE
			SYNTAX OCTET STRING (SIZE (0..12))
			MAX-ACCESS read-create
			STATUS current
			DESCRIPTION
				"password"
			::= { topOnuAuthLogicSnEntry 6 }

		
		-- 1.3.6.1.4.1.32285.11.2.3.4.2.1.1.7
		topOnuAuthLogicSnAction OBJECT-TYPE
			SYNTAX INTEGER
				{
				accept(1),
				reject(2)
				}
			MAX-ACCESS read-create
			STATUS current
			DESCRIPTION
				"Authen Action
				This is optional in function"
			DEFVAL { 1 }
			::= { topOnuAuthLogicSnEntry 7 }

		
		-- 1.3.6.1.4.1.32285.11.2.3.4.2.1.1.8
		topOnuAuthLogicSnRowStatus OBJECT-TYPE
			SYNTAX RowStatus
			MAX-ACCESS read-create
			STATUS current
			DESCRIPTION
				"authen Row Status"
			::= { topOnuAuthLogicSnEntry 8 }


		-- 1.3.6.1.4.1.32285.11.2.3.4.2.2
		topOnuAuthBlockExtTable OBJECT-TYPE
			SYNTAX SEQUENCE OF TopOnuAuthBlockExtEntry
			MAX-ACCESS not-accessible
			STATUS current
			DESCRIPTION
				"A list of topOnuAuthBlockExtTable entries. "
			::= { topOnuAuthMgmt 2 }

		
		-- 1.3.6.1.4.1.32285.11.2.3.4.2.2.1
		topOnuAuthBlockExtEntry OBJECT-TYPE
			SYNTAX TopOnuAuthBlockExtEntry
			MAX-ACCESS not-accessible
			STATUS current
			DESCRIPTION
				"unauthorized onu information.
				Index depends on onuAuthenBlockOnuId, defined in onuAuthenticationBlockTable of NSCRTV MIB.
				This information will be read only, not support row-status operation.
				In case of implementation ONU authentication, just config onu in advance."
			INDEX { topOnuAuthBlockExtOnuId }
			::= { topOnuAuthBlockExtTable 1 }

		
		TopOnuAuthBlockExtEntry ::=
			SEQUENCE { 
				topOnuAuthBlockExtOnuId
					EponDeviceIndex,
				topOnuAuthBlockedExtLogicSn
					OCTET STRING,
				topOnuAuthBlockedExtPwd
					OCTET STRING
			 }

		-- 1.3.6.1.4.1.32285.11.2.3.4.2.2.1.1
		topOnuAuthBlockExtOnuId OBJECT-TYPE
			SYNTAX EponDeviceIndex
			MAX-ACCESS not-accessible
			STATUS current
			DESCRIPTION
				"ONU Id"
			::= { topOnuAuthBlockExtEntry 1 }

		
		-- 1.3.6.1.4.1.32285.11.2.3.4.2.2.1.2
		topOnuAuthBlockedExtLogicSn OBJECT-TYPE
			SYNTAX OCTET STRING (SIZE (0..24))
			MAX-ACCESS read-only
			STATUS current
			DESCRIPTION
				"logic sn"
			::= { topOnuAuthBlockExtEntry 2 }

		
		-- 1.3.6.1.4.1.32285.11.2.3.4.2.2.1.3
		topOnuAuthBlockedExtPwd OBJECT-TYPE
			SYNTAX OCTET STRING (SIZE (0..12))
			MAX-ACCESS read-only
			STATUS current
			DESCRIPTION
				"password"
			::= { topOnuAuthBlockExtEntry 3 }

		
		-- 1.3.6.1.4.1.32285.11.2.3.4.2.3
		topOnuProductTable OBJECT-TYPE
			SYNTAX SEQUENCE OF TopOnuProductEntry
			MAX-ACCESS not-accessible
			STATUS current
			DESCRIPTION
				"ONU pre auth product table."
			::= { topOnuAuthMgmt 3 }

		
		-- 1.3.6.1.4.1.32285.11.2.3.4.2.3.1
		topOnuProductEntry OBJECT-TYPE
			SYNTAX TopOnuProductEntry
			MAX-ACCESS not-accessible
			STATUS current
			DESCRIPTION
				"ONU pre auth product table entry."
			INDEX { topOnuProductCardIndex, topOnuProductPonIndex, topOnuProductOnuIndex }
			::= { topOnuProductTable 1 }

		
		TopOnuProductEntry ::=
			SEQUENCE { 
				topOnuProductCardIndex
					TopEPonSlotIndex,
				topOnuProductPonIndex
					TopEPonPonIndex,
				topOnuProductOnuIndex
					TopEPonOnuAuthNum,
				topOnuProductType
					OCTET STRING
			 }

		-- 1.3.6.1.4.1.32285.11.2.3.4.2.3.1.1
		topOnuProductCardIndex OBJECT-TYPE
			SYNTAX TopEPonSlotIndex
			MAX-ACCESS not-accessible
			STATUS current
			DESCRIPTION
				"Slot index."
			::= { topOnuProductEntry 1 }

		
		-- 1.3.6.1.4.1.32285.11.2.3.4.2.3.1.2
		topOnuProductPonIndex OBJECT-TYPE
			SYNTAX TopEPonPonIndex
			MAX-ACCESS not-accessible
			STATUS current
			DESCRIPTION
				"pon port index."
			::= { topOnuProductEntry 2 }

		
		-- 1.3.6.1.4.1.32285.11.2.3.4.2.3.1.3
		topOnuProductOnuIndex OBJECT-TYPE
			SYNTAX TopEPonOnuAuthNum
			MAX-ACCESS not-accessible
			STATUS current
			DESCRIPTION
				"onu id index."
			::= { topOnuProductEntry 3 }

		
		-- 1.3.6.1.4.1.32285.11.2.3.4.2.3.1.4
		topOnuProductType OBJECT-TYPE
			SYNTAX OCTET STRING
			MAX-ACCESS read-write
			STATUS current
			DESCRIPTION
				"Onu product name,Set the product like this:
                '8621'-PN8621
                '8622'-PN8622
                '8623'-PN8623
                '8624'-PN8624
                '8625'-PN8625
                '8641'-PN8641
                '8643'-PN8643
                '8645'-PN8645
                'none'-Other onu types."
			::= { topOnuProductEntry 4 }
			
		-- 1.3.6.1.4.1.32285.11.2.3.4.3
		topOnuRstpMgmtObjects OBJECT IDENTIFIER ::= { topOnuObjects 3 }

		
		-- 1.3.6.1.4.1.32285.11.2.3.4.3.1
		topOnuRstpConfigTable OBJECT-TYPE
			SYNTAX SEQUENCE OF TopOnuRstpConfigEntry
			MAX-ACCESS not-accessible
			STATUS current
			DESCRIPTION
				"ONU RSTP config table"
			::= { topOnuRstpMgmtObjects 1 }

		
		-- 1.3.6.1.4.1.32285.11.2.3.4.3.1.1
		topOnuRstpConfigEntry OBJECT-TYPE
			SYNTAX TopOnuRstpConfigEntry
			MAX-ACCESS not-accessible
			STATUS current
			DESCRIPTION
				"The onuInfoEntry Information"
			INDEX { topOnuRstpCardIndex, topOnuRstpPonIndex, topOnuRstpOnuIndex }
			::= { topOnuRstpConfigTable 1 }

		
		TopOnuRstpConfigEntry ::=
			SEQUENCE { 
				topOnuRstpCardIndex
					TopEPonSlotIndex,
				topOnuRstpPonIndex
					TopEPonPonIndex,
				topOnuRstpOnuIndex
					TopEPonOnuAuthNum,
				topOnuRstpBridgeMode
					INTEGER
			 }

		-- 1.3.6.1.4.1.32285.11.2.3.4.3.1.1.1
		topOnuRstpCardIndex OBJECT-TYPE
			SYNTAX TopEPonSlotIndex
			MAX-ACCESS not-accessible
			STATUS current
			DESCRIPTION
				"slot Index"
			::= { topOnuRstpConfigEntry 1 }

		
		-- 1.3.6.1.4.1.32285.11.2.3.4.3.1.1.2
		topOnuRstpPonIndex OBJECT-TYPE
			SYNTAX TopEPonPonIndex
			MAX-ACCESS not-accessible
			STATUS current
			DESCRIPTION
				"pon Index"
			::= { topOnuRstpConfigEntry 2 }

		
		-- 1.3.6.1.4.1.32285.11.2.3.4.3.1.1.3
		topOnuRstpOnuIndex OBJECT-TYPE
			SYNTAX TopEPonOnuAuthNum
			MAX-ACCESS not-accessible
			STATUS current
			DESCRIPTION
				"ONU auth Index"
			::= { topOnuRstpConfigEntry 3 }

		
		-- 1.3.6.1.4.1.32285.11.2.3.4.3.1.1.4
		topOnuRstpBridgeMode OBJECT-TYPE
			SYNTAX INTEGER
				{
				enable(1),
				disable(2),
				passThrough(3)
				}
			MAX-ACCESS read-write
			STATUS current
			DESCRIPTION
				"onu rstp mode"
			DEFVAL { 2 }
			::= { topOnuRstpConfigEntry 4 }

		
		-- 1.3.6.1.4.1.32285.11.2.3.4.4
		topOnuVoipMgmtObjects OBJECT IDENTIFIER ::= { topOnuObjects 4 }

		
		-- 1.3.6.1.4.1.32285.11.2.3.4.4.1
		topOnuVoipConfigTable OBJECT-TYPE
			SYNTAX SEQUENCE OF TopOnuVoipConfigEntry
			MAX-ACCESS not-accessible
			STATUS current
			DESCRIPTION
				"ONU RSTP config table"
			::= { topOnuVoipMgmtObjects 1 }

		
		-- 1.3.6.1.4.1.32285.11.2.3.4.4.1.1
		topOnuVoipConfigEntry OBJECT-TYPE
			SYNTAX TopOnuVoipConfigEntry
			MAX-ACCESS not-accessible
			STATUS current
			DESCRIPTION
				"The onuInfoEntry Information"
			INDEX { topOnuVoipCardIndex, topOnuVoipPonIndex, topOnuVoipOnuIndex }
			::= { topOnuVoipConfigTable 1 }

		
		TopOnuVoipConfigEntry ::=
			SEQUENCE { 
				topOnuVoipCardIndex
					TopEPonSlotIndex,
				topOnuVoipPonIndex
					TopEPonPonIndex,
				topOnuVoipOnuIndex
					TopEPonOnuAuthNum,
				topOnuVoipEnable
					INTEGER
			 }

		-- 1.3.6.1.4.1.32285.11.2.3.4.4.1.1.1
		topOnuVoipCardIndex OBJECT-TYPE
			SYNTAX TopEPonSlotIndex
			MAX-ACCESS not-accessible
			STATUS current
			DESCRIPTION
				"slot Index"
			::= { topOnuVoipConfigEntry 1 }

		
		-- 1.3.6.1.4.1.32285.11.2.3.4.4.1.1.2
		topOnuVoipPonIndex OBJECT-TYPE
			SYNTAX TopEPonPonIndex
			MAX-ACCESS not-accessible
			STATUS current
			DESCRIPTION
				"pon Index"
			::= { topOnuVoipConfigEntry 2 }

		
		-- 1.3.6.1.4.1.32285.11.2.3.4.4.1.1.3
		topOnuVoipOnuIndex OBJECT-TYPE
			SYNTAX TopEPonOnuAuthNum
			MAX-ACCESS not-accessible
			STATUS current
			DESCRIPTION
				"ONU auth Index"
			::= { topOnuVoipConfigEntry 3 }

		
		-- 1.3.6.1.4.1.32285.11.2.3.4.4.1.1.4
		topOnuVoipEnable OBJECT-TYPE
			SYNTAX INTEGER
				{
				enable(1),
				disable(2)
				}
			MAX-ACCESS read-write
			STATUS current
			DESCRIPTION
				"ONU VoIP config, not supported at present"
			DEFVAL { 2 }
			::= { topOnuVoipConfigEntry 4 }

		
		-- 1.3.6.1.4.1.32285.11.2.3.4.5
		topOnuCatvMgmtObjects OBJECT IDENTIFIER ::= { topOnuObjects 5 }

		
		-- 1.3.6.1.4.1.32285.11.2.3.4.5.1
		topOnuCatvConfigTable OBJECT-TYPE
			SYNTAX SEQUENCE OF TopOnuCatvConfigEntry
			MAX-ACCESS not-accessible
			STATUS current
			DESCRIPTION
				"ONU RSTP config table"
			::= { topOnuCatvMgmtObjects 1 }

		
		-- 1.3.6.1.4.1.32285.11.2.3.4.5.1.1
		topOnuCatvConfigEntry OBJECT-TYPE
			SYNTAX TopOnuCatvConfigEntry
			MAX-ACCESS not-accessible
			STATUS current
			DESCRIPTION
				"The onuInfoEntry Information"
			INDEX { topOnuCatvCardIndex, topOnuCatvPonIndex, topOnuCatvOnuIndex }
			::= { topOnuCatvConfigTable 1 }

		
		TopOnuCatvConfigEntry ::=
			SEQUENCE { 
				topOnuCatvCardIndex
					TopEPonSlotIndex,
				topOnuCatvPonIndex
					TopEPonPonIndex,
				topOnuCatvOnuIndex
					TopEPonOnuAuthNum,
				topOnuCatvEnable
					INTEGER
			 }

		-- 1.3.6.1.4.1.32285.11.2.3.4.5.1.1.1
		topOnuCatvCardIndex OBJECT-TYPE
			SYNTAX TopEPonSlotIndex
			MAX-ACCESS not-accessible
			STATUS current
			DESCRIPTION
				"slot Index"
			::= { topOnuCatvConfigEntry 1 }

		
		-- 1.3.6.1.4.1.32285.11.2.3.4.5.1.1.2
		topOnuCatvPonIndex OBJECT-TYPE
			SYNTAX TopEPonPonIndex
			MAX-ACCESS not-accessible
			STATUS current
			DESCRIPTION
				"pon Index"
			::= { topOnuCatvConfigEntry 2 }

		
		-- 1.3.6.1.4.1.32285.11.2.3.4.5.1.1.3
		topOnuCatvOnuIndex OBJECT-TYPE
			SYNTAX TopEPonOnuAuthNum
			MAX-ACCESS not-accessible
			STATUS current
			DESCRIPTION
				"ONU auth Index"
			::= { topOnuCatvConfigEntry 3 }

		
		-- 1.3.6.1.4.1.32285.11.2.3.4.5.1.1.4
		topOnuCatvEnable OBJECT-TYPE
			SYNTAX INTEGER
				{
				enable(1),
				disable(2)
				}
			MAX-ACCESS read-write
			STATUS current
			DESCRIPTION
				"ONU VoIP config, not supported at present"
			DEFVAL { 2 }
			::= { topOnuCatvConfigEntry 4 }

		
		-- 1.3.6.1.4.1.32285.11.2.3.4.6
		topOnuUpgradeMgmtObjects OBJECT IDENTIFIER ::= { topOnuObjects 6 }

		
		-- 1.3.6.1.4.1.32285.11.2.3.4.6.1
		topOnuUpgradeTable OBJECT-TYPE
			SYNTAX SEQUENCE OF TopOnuUpgradeEntry
			MAX-ACCESS not-accessible
			STATUS current
			DESCRIPTION
				"ONU batch upgrading table"
			::= { topOnuUpgradeMgmtObjects 1 }

		
		-- 1.3.6.1.4.1.32285.11.2.3.4.6.1.1
		topOnuUpgradeEntry OBJECT-TYPE
			SYNTAX TopOnuUpgradeEntry
			MAX-ACCESS not-accessible
			STATUS current
			DESCRIPTION
				"The onu batch upgrading entry"
			INDEX { topOnuUpgradeTransactionIndex }
			::= { topOnuUpgradeTable 1 }

		
		TopOnuUpgradeEntry ::=
			SEQUENCE { 
				topOnuUpgradeTransactionIndex
					INTEGER,
				topOnuUpgradeSlotNum
					TopEPonSlotIndex,
				topOnuUpgradeOnuType
					INTEGER,
				topOnuUpgradeFileName
					OCTET STRING,
				topOnuUpgradeFileType
					INTEGER,
				topOnuUpgradeMode
					INTEGER,
				topOnuUpgradeOnuList
					OCTET STRING,
				topOnuUpgradeOperAction
					INTEGER,
				topOnuUpgradeStatus
					OCTET STRING,
				topOnuUpgradeRowStatus
					RowStatus
			 }

		-- 1.3.6.1.4.1.32285.11.2.3.4.6.1.1.1
		topOnuUpgradeTransactionIndex OBJECT-TYPE
			SYNTAX INTEGER
			MAX-ACCESS not-accessible
			STATUS current
			DESCRIPTION
				"The ID of Transaction its belongs to.
				Support max 100 records,
				otherwise delete previous transactions firstly"
			::= { topOnuUpgradeEntry 1 }

		
		-- 1.3.6.1.4.1.32285.11.2.3.4.6.1.1.2
		topOnuUpgradeSlotNum OBJECT-TYPE
			SYNTAX TopEPonSlotIndex
			MAX-ACCESS read-create
			STATUS current
			DESCRIPTION
				"This object makes sense in two cases. 
				One is to provide number of slot which will download its bootrom/app 
				files from the SCU ramdisk into its own Flash memory. 
				The other is to provide number of slot which the OLT/ONUs who will 
				download their firmware files from the SCU ramdisk into their own Flash memory 
				reside on."
			::= { topOnuUpgradeEntry 2 }

		
		-- 1.3.6.1.4.1.32285.11.2.3.4.6.1.1.3
		topOnuUpgradeOnuType OBJECT-TYPE
			SYNTAX INTEGER
			MAX-ACCESS read-create
			STATUS current
			DESCRIPTION
				"An integer value to identify the Onu Type to be upgraded,
				as per product plan."
			::= { topOnuUpgradeEntry 3 }

		
		-- 1.3.6.1.4.1.32285.11.2.3.4.6.1.1.4
		topOnuUpgradeFileName OBJECT-TYPE
			SYNTAX OCTET STRING (SIZE (1..63))
			MAX-ACCESS read-create
			STATUS current
			DESCRIPTION
				"This is the name of the source file name, including file path."
			::= { topOnuUpgradeEntry 4 }

		
		-- 1.3.6.1.4.1.32285.11.2.3.4.6.1.1.5
		topOnuUpgradeFileType OBJECT-TYPE
			SYNTAX INTEGER
				{
				onuBoot(9),
				onuConfig(10),
				onuFirmware(11),
				onuApp(12),
				onuCombinedPkg(13)
				}
			MAX-ACCESS read-create
			STATUS current
			DESCRIPTION
				"This object indicates the file type of operation to be performed.   		 
				Selecting boot(9)/config(10)/firmware(11)/app(12)/onuCombinedPkg(12)
				will perform an upgrade operation to ONU chipset(s).
				For onuCombinedPkg(13), OLT will check package header so as to
				decided whether spliting package into multi sub-package or not,
				then sending them to ONU. If OLT can not anlyzer the package head,
				it will send them to ONU directly as one package."
			DEFVAL { 13 }
			::= { topOnuUpgradeEntry 5 }

		
		-- 1.3.6.1.4.1.32285.11.2.3.4.6.1.1.6
		topOnuUpgradeMode OBJECT-TYPE
			SYNTAX INTEGER
				{
				tk(1),
				pmc(2),
				ctc(4)
				}
			MAX-ACCESS read-create
			STATUS current
			DESCRIPTION
				"The Quantity of Onus to be upgraded.
				At present, ctc mode supported only,
				other value reserved for future extension.
				"
			DEFVAL { 4 }
			::= { topOnuUpgradeEntry 6 }

		
		-- 1.3.6.1.4.1.32285.11.2.3.4.6.1.1.7
		topOnuUpgradeOnuList OBJECT-TYPE
			SYNTAX OCTET STRING (SIZE (1024 | 2048))
			MAX-ACCESS read-create
			STATUS current
			DESCRIPTION
				"The first 128 octets indicate those ONUs under PON index 1,
				the second 128 octets indicate those ONUs under PON index 2,
				So the max ONU quantity is 2048/128=16 PONs under one slot.
				In case some ONUs do not exist, just filled with 0x00.
				"
			::= { topOnuUpgradeEntry 7 }

		
		-- 1.3.6.1.4.1.32285.11.2.3.4.6.1.1.8
		topOnuUpgradeOperAction OBJECT-TYPE
			SYNTAX INTEGER
				{
				none(0),
				upgrade(1)
				}
			MAX-ACCESS read-create
			STATUS current
			DESCRIPTION
				"This is the action to be taken to start the upgrade operation."
			::= { topOnuUpgradeEntry 8 }

		
		-- 1.3.6.1.4.1.32285.11.2.3.4.6.1.1.9
		topOnuUpgradeStatus OBJECT-TYPE
			SYNTAX OCTET STRING (SIZE (2048))
			MAX-ACCESS read-create
			STATUS current
			DESCRIPTION
				"This variable is the result of the upgrade operation.
				1.Each OCTET represent the upgrading status of one ONU.
				From left to right, the first OCTET indicate the result of PON 1 ONU 1,
				then PON 1 ONU 2, and so on.
				the 1024 octet indicate the result of PON 16 ONU 128.
				2.In one OCTET,	idle(1), inProgress(2), success(3), failure(4),
				other values are reserved and meaningless.
				"
			::= { topOnuUpgradeEntry 9 }

		
		-- 1.3.6.1.4.1.32285.11.2.3.4.6.1.1.10
		topOnuUpgradeRowStatus OBJECT-TYPE
			SYNTAX RowStatus
			MAX-ACCESS read-create
			STATUS current
			DESCRIPTION
				"add/del/set"
			::= { topOnuUpgradeEntry 10 }

		
		-- 1.3.6.1.4.1.32285.11.2.3.4.7
		topOnuAutoUpgardeMgmtObjects OBJECT IDENTIFIER ::= { topOnuObjects 7 }

		
		-- 1.3.6.1.4.1.32285.11.2.3.4.7.1
		topOnuAutoUpgradeTable OBJECT-TYPE
			SYNTAX SEQUENCE OF TopOnuAutoUpgradeEntry
			MAX-ACCESS not-accessible
			STATUS current
			DESCRIPTION
				"ONU batch upgrading table"
			::= { topOnuAutoUpgardeMgmtObjects 1 }

		
		-- 1.3.6.1.4.1.32285.11.2.3.4.7.1.1
		topOnuAutoUpgradeEntry OBJECT-TYPE
			SYNTAX TopOnuAutoUpgradeEntry
			MAX-ACCESS not-accessible
			STATUS current
			DESCRIPTION
				"The onu batch upgrading entry"
			INDEX { topOnuAutoUpgradeIndex }
			::= { topOnuAutoUpgradeTable 1 }

		
		TopOnuAutoUpgradeEntry ::=
			SEQUENCE { 
				topOnuAutoUpgradeIndex
					INTEGER,
				topOnuAutoUpgradeOnuType
					INTEGER,
				topOnuAutoUpgradeNewVersion
					INTEGER,
				topOnuAutoUpgradeEnable
					INTEGER,
				topOnuAutoUpgradeTime
					INTEGER,
				topOnuAutoUpgradeFileName
					OCTET STRING,
				topOnuAutoUpgradeFileType
					INTEGER,
				topOnuAutoUpgradeMode
					INTEGER,
				topOnuAutoUpgradeRowStatus
					RowStatus
			 }

		-- 1.3.6.1.4.1.32285.11.2.3.4.7.1.1.1
		topOnuAutoUpgradeIndex OBJECT-TYPE
			SYNTAX INTEGER
			MAX-ACCESS not-accessible
			STATUS current
			DESCRIPTION
				"The ID of Transaction its belongs to. "
			::= { topOnuAutoUpgradeEntry 1 }

		
		-- 1.3.6.1.4.1.32285.11.2.3.4.7.1.1.2
		topOnuAutoUpgradeOnuType OBJECT-TYPE
			SYNTAX INTEGER
			MAX-ACCESS read-write
			STATUS current
			DESCRIPTION
				"The Onu Type of Transaction its belongs to."
			::= { topOnuAutoUpgradeEntry 2 }

		
		-- 1.3.6.1.4.1.32285.11.2.3.4.7.1.1.3
		topOnuAutoUpgradeNewVersion OBJECT-TYPE
			SYNTAX INTEGER
			MAX-ACCESS read-write
			STATUS current
			DESCRIPTION
				"This object makes sense in two cases. 
				One is to provide number of slot which will download its bootrom/app 
				files from the SCU ramdisk into its own Flash memory. 
				The other is to provide number of slot which the OLT/ONUs who will 
				download their firmware files from the SCU ramdisk into their own Flash memory 
				reside on."
			::= { topOnuAutoUpgradeEntry 3 }

		
		-- 1.3.6.1.4.1.32285.11.2.3.4.7.1.1.4
		topOnuAutoUpgradeEnable OBJECT-TYPE
			SYNTAX INTEGER
				{
				enable(1),
				disable(2)
				}
			MAX-ACCESS read-write
			STATUS current
			DESCRIPTION
				"enable-1, disable-2"
			::= { topOnuAutoUpgradeEntry 4 }

		
		-- 1.3.6.1.4.1.32285.11.2.3.4.7.1.1.5
		topOnuAutoUpgradeTime OBJECT-TYPE
			SYNTAX INTEGER
			MAX-ACCESS read-write
			STATUS current
			DESCRIPTION
				"0xFFFF indicate the spicific ONU will be upgraded automatically
				at any time.
				Otherwise, they will upgarde at the specfic time."
			::= { topOnuAutoUpgradeEntry 5 }

		
		-- 1.3.6.1.4.1.32285.11.2.3.4.7.1.1.6
		topOnuAutoUpgradeFileName OBJECT-TYPE
			SYNTAX OCTET STRING (SIZE (0..255))
			MAX-ACCESS read-write
			STATUS current
			DESCRIPTION
				"This is the name of the source file name, including file path."
			::= { topOnuAutoUpgradeEntry 6 }

		
		-- 1.3.6.1.4.1.32285.11.2.3.4.7.1.1.7
		topOnuAutoUpgradeFileType OBJECT-TYPE
			SYNTAX INTEGER
				{
				onuBoot(9),
				onuConfig(10),
				onuFirmware(11),
				onuApp(12),
				onuCombinedPkg(13)
				}
			MAX-ACCESS read-write
			STATUS current
			DESCRIPTION
				"This object indicates the file type of operation to be performed.   		 
				Selecting boot(9)/config(10)/firmware(11)/app(12)/onuCombinedPkg(12)
				will perform an upgrade operation to ONU chipset(s).
				For onuCombinedPkg(13), OLT will check package header so as to
				decided whether spliting package into multi sub-package or not,
				then sending them to ONU. If OLT can not anlyzer the package head,
				it will send them to ONU directly as one package."
			::= { topOnuAutoUpgradeEntry 7 }

		
		-- 1.3.6.1.4.1.32285.11.2.3.4.7.1.1.8
		topOnuAutoUpgradeMode OBJECT-TYPE
			SYNTAX INTEGER
				{
				tk(1),
				pmc(2),
				ctc(4)
				}
			MAX-ACCESS read-write
			STATUS current
			DESCRIPTION
				"The Quantity of Onus to be upgraded."
			::= { topOnuAutoUpgradeEntry 8 }

		
		-- 1.3.6.1.4.1.32285.11.2.3.4.7.1.1.9
		topOnuAutoUpgradeRowStatus OBJECT-TYPE
			SYNTAX RowStatus
			MAX-ACCESS read-only
			STATUS current
			DESCRIPTION
				"add/del/set"
			::= { topOnuAutoUpgradeEntry 9 }


		-- 1.3.6.1.4.1.32285.11.2.3.4.8
		topOnuModifyTable OBJECT-TYPE
			SYNTAX SEQUENCE OF TopOnuModifyEntry
			MAX-ACCESS not-accessible
			STATUS current
			DESCRIPTION
				"ONU replace table"
			::= { topOnuObjects 8 }

		
		-- 1.3.6.1.4.1.32285.11.2.3.4.8.1
		topOnuModifyEntry OBJECT-TYPE
			SYNTAX TopOnuModifyEntry
			MAX-ACCESS not-accessible
			STATUS current
			DESCRIPTION
				"ONU replace entry.
				supported mode:MAC only, sn only, password only,sn+password,
				other mode will not be supported at present."
			INDEX { topOnuModifyCardIndex, topOnuModifyPonIndex, topOnuModifyOnuIndex }
			::= { topOnuModifyTable 1 }

		
		TopOnuModifyEntry ::=
			SEQUENCE { 
				topOnuModifyCardIndex
					TopEPonSlotIndex,
				topOnuModifyPonIndex
					TopEPonPonIndex,
				topOnuModifyOnuIndex
					TopEPonOnuAuthNum,
				topOnuModifyMacAddress
					MacAddress,
				topOnuModifyLogicSn
					OCTET STRING,
				topOnuModifyPwd
					OCTET STRING
			 }

		-- 1.3.6.1.4.1.32285.11.2.3.4.8.1.1
		topOnuModifyCardIndex OBJECT-TYPE
			SYNTAX TopEPonSlotIndex
			MAX-ACCESS not-accessible
			STATUS current
			DESCRIPTION
				"onu slot Index"
			::= { topOnuModifyEntry 1 }

		
		-- 1.3.6.1.4.1.32285.11.2.3.4.8.1.2
		topOnuModifyPonIndex OBJECT-TYPE
			SYNTAX TopEPonPonIndex
			MAX-ACCESS not-accessible
			STATUS current
			DESCRIPTION
				"onu pon Index"
			::= { topOnuModifyEntry 2 }

		
		-- 1.3.6.1.4.1.32285.11.2.3.4.8.1.3
		topOnuModifyOnuIndex OBJECT-TYPE
			SYNTAX TopEPonOnuAuthNum
			MAX-ACCESS not-accessible
			STATUS current
			DESCRIPTION
				"onu auth Index"
			::= { topOnuModifyEntry 3 }

		
		-- 1.3.6.1.4.1.32285.11.2.3.4.8.1.4
		topOnuModifyMacAddress OBJECT-TYPE
			SYNTAX MacAddress
			MAX-ACCESS read-write
			STATUS current
			DESCRIPTION
				"Mac Address.
				Filling six bytes with 0x00, means invalid this member."
			::= { topOnuModifyEntry 4 }

		
		-- 1.3.6.1.4.1.32285.11.2.3.4.8.1.5
		topOnuModifyLogicSn OBJECT-TYPE
			SYNTAX OCTET STRING (SIZE (0..24))
			MAX-ACCESS read-write
			STATUS current
			DESCRIPTION
				"logic sn."
			::= { topOnuModifyEntry 5 }

		
		-- 1.3.6.1.4.1.32285.11.2.3.4.8.1.6
		topOnuModifyPwd OBJECT-TYPE
			SYNTAX OCTET STRING (SIZE (0..12))
			MAX-ACCESS read-write
			STATUS current
			DESCRIPTION
				"password"
			::= { topOnuModifyEntry 6 }

		
		-- 1.3.6.1.4.1.32285.11.2.3.5
		topUniObjects OBJECT IDENTIFIER ::= { topvisionEponTree 5 }

		
		-- 1.3.6.1.4.1.32285.11.2.3.5.1
		topUniAttrTable OBJECT-TYPE
			SYNTAX SEQUENCE OF TopUniAttrEntry
			MAX-ACCESS not-accessible
			STATUS current
			DESCRIPTION
				"A list of topUniAttrTable entries."
			::= { topUniObjects 1 }

		
		-- 1.3.6.1.4.1.32285.11.2.3.5.1.1
		topUniAttrEntry OBJECT-TYPE
			SYNTAX TopUniAttrEntry
			MAX-ACCESS not-accessible
			STATUS current
			DESCRIPTION
				"The topUniAttrEntry Information"
			INDEX { topUniAttrCardIndex, topUniAttrPonIndex, topUniAttrOnuIndex, topUniAttrPortIndex }
			::= { topUniAttrTable 1 }

		
		TopUniAttrEntry ::=
			SEQUENCE { 
				topUniAttrCardIndex
					TopEPonSlotIndex,
				topUniAttrPonIndex
					TopEPonPonIndex,
				topUniAttrOnuIndex
					TopEPonOnuAuthNum,
				topUniAttrPortIndex
					TopEPonUniPortIndex,
				topUniAttrFlowCtrl
					INTEGER,
				topUniAttrPerfStats15minuteEnable
					INTEGER,
				topUniAttrPerfStats24hourEnable
					INTEGER,
				topUniAttrLastChangeTime
					TimeTicks,
				topUniAttrIsolationEnable
					INTEGER,
				topUniAttrMacAddrLearnMaxNum
					INTEGER,
				topUniAttrAutoNegotiationAdvertisedTechAbility
					BITS,
				topUniAttrMacAddrClearByPort
					INTEGER,
                topUniAttrMacAge
					INTEGER
			 }

		-- 1.3.6.1.4.1.32285.11.2.3.5.1.1.1
		topUniAttrCardIndex OBJECT-TYPE
			SYNTAX TopEPonSlotIndex
			MAX-ACCESS not-accessible
			STATUS current
			DESCRIPTION
				"Card Index
				The value of this cardIndex depends on onuType.
				fixed(1) - set to 0, to indicate slot num is meaningless.
				chassisBased(2) - MUST NOT be zero
				"
			::= { topUniAttrEntry 1 }

		
		-- 1.3.6.1.4.1.32285.11.2.3.5.1.1.2
		topUniAttrPonIndex OBJECT-TYPE
			SYNTAX TopEPonPonIndex
			MAX-ACCESS not-accessible
			STATUS current
			DESCRIPTION
				"Pon index"
			::= { topUniAttrEntry 2 }

		
		-- 1.3.6.1.4.1.32285.11.2.3.5.1.1.3
		topUniAttrOnuIndex OBJECT-TYPE
			SYNTAX TopEPonOnuAuthNum
			MAX-ACCESS not-accessible
			STATUS current
			DESCRIPTION
				"Pon index"
			::= { topUniAttrEntry 3 }

		
		-- 1.3.6.1.4.1.32285.11.2.3.5.1.1.4
		topUniAttrPortIndex OBJECT-TYPE
			SYNTAX TopEPonUniPortIndex
			MAX-ACCESS not-accessible
			STATUS current
			DESCRIPTION
				"Port Index"
			::= { topUniAttrEntry 4 }

		
		-- 1.3.6.1.4.1.32285.11.2.3.5.1.1.5
		topUniAttrFlowCtrl OBJECT-TYPE
			SYNTAX INTEGER
				{
				enable(1),
				disable(2)
				}
			MAX-ACCESS read-write
			STATUS current
			DESCRIPTION
				"Port Index"
			DEFVAL { 2 }
			::= { topUniAttrEntry 5 }

		
		-- 1.3.6.1.4.1.32285.11.2.3.5.1.1.6
		topUniAttrPerfStats15minuteEnable OBJECT-TYPE
			SYNTAX INTEGER
				{
				true(1),
				false(2)
				}
			MAX-ACCESS read-write
			STATUS current
			DESCRIPTION
				"Description."
			DEFVAL { 2 }
			::= { topUniAttrEntry 6 }

		
		-- 1.3.6.1.4.1.32285.11.2.3.5.1.1.7
		topUniAttrPerfStats24hourEnable OBJECT-TYPE
			SYNTAX INTEGER
				{
				true(1),
				false(2)
				}
			MAX-ACCESS read-write
			STATUS current
			DESCRIPTION
				"Description."
			DEFVAL { 2 }
			::= { topUniAttrEntry 7 }

		
		-- 1.3.6.1.4.1.32285.11.2.3.5.1.1.8
		topUniAttrLastChangeTime OBJECT-TYPE
			SYNTAX TimeTicks
			MAX-ACCESS read-only
			STATUS current
			DESCRIPTION
				"Description."
			::= { topUniAttrEntry 8 }

		
		-- 1.3.6.1.4.1.32285.11.2.3.5.1.1.9
		topUniAttrIsolationEnable OBJECT-TYPE
			SYNTAX INTEGER
				{
				true(1),
				false(2)
				}
			MAX-ACCESS read-write
			STATUS current
			DESCRIPTION
				"Description."
			::= { topUniAttrEntry 9 }

		
		-- 1.3.6.1.4.1.32285.11.2.3.5.1.1.10
		topUniAttrMacAddrLearnMaxNum OBJECT-TYPE
			SYNTAX INTEGER
			MAX-ACCESS read-write
			STATUS current
			DESCRIPTION
				"Description."
			DEFVAL { ''b }
			::= { topUniAttrEntry 10 }

		
		-- 1.3.6.1.4.1.32285.11.2.3.5.1.1.11
		topUniAttrAutoNegotiationAdvertisedTechAbility OBJECT-TYPE
			SYNTAX BITS
				{
				oneBaseTHalfDuplex(0),
				tenBaseTFullDuplex(1),
				tenBaseTHalfDuplex(2),
				hundredBaseTFullDuplex(3),
				hundredBaseTHalfDuplex(4),
				thousandBaseTFullDuplex(5),
				thousandBaseTHalfDuplex(6),
				thousandBaseXFullDuplex(7),
				thousandBaseXHalfDuplex(8),
				fdxPause(9),
				fdxApause(10),
				fdxSpause(11),
				fdxBpause(12)
				}
			MAX-ACCESS read-write
			STATUS current
			DESCRIPTION
				"Description."
			::= { topUniAttrEntry 11 }

		
		-- 1.3.6.1.4.1.32285.11.2.3.5.1.1.12
		topUniAttrMacAddrClearByPort OBJECT-TYPE
			SYNTAX INTEGER { clearDynamic(1) }
			MAX-ACCESS read-write
			STATUS current
			DESCRIPTION
				"Description."
			::= { topUniAttrEntry 12 }

        -- 1.3.6.1.4.1.32285.11.2.3.5.1.1.13
		topUniAttrMacAge OBJECT-TYPE
			SYNTAX INTEGER 
			MAX-ACCESS read-write
			STATUS current
			DESCRIPTION
				"Mac Address Table Aging Time"
			::= { topUniAttrEntry 13 }
		
		-- 1.3.6.1.4.1.32285.11.2.3.5.2
		topUniBroadcastStormSuppressionTable OBJECT-TYPE
			SYNTAX SEQUENCE OF TopUniBroadcastStormSuppressionEntry
			MAX-ACCESS not-accessible
			STATUS current
			DESCRIPTION
				"Description."
			::= { topUniObjects 2 }

		
		-- 1.3.6.1.4.1.32285.11.2.3.5.2.1
		topUniBroadcastStormSuppressionEntry OBJECT-TYPE
			SYNTAX TopUniBroadcastStormSuppressionEntry
			MAX-ACCESS not-accessible
			STATUS current
			DESCRIPTION
				"Description."
			INDEX { topUniBroadcastStormSuppressionCardIndex, topUniBroadcastStormSuppressionPonIndex, topUniBroadcastStormSuppressionOnuIndex, topUniBroadcastStormSuppressionPortIndex }
			::= { topUniBroadcastStormSuppressionTable 1 }

		
		TopUniBroadcastStormSuppressionEntry ::=
			SEQUENCE { 
				topUniBroadcastStormSuppressionCardIndex
					TopEPonSlotIndex,
				topUniBroadcastStormSuppressionPonIndex
					TopEPonPonIndex,
				topUniBroadcastStormSuppressionOnuIndex
					TopEPonOnuAuthNum,
				topUniBroadcastStormSuppressionPortIndex
					TopEPonUniPortIndex,
				topUniUnicastStormEnable
					INTEGER,
				topUniUnicastStormInPacketRate
					INTEGER,
				topUniUnicastStormOutPacketRate
					INTEGER,
				topUniMulticastStormEnable
					INTEGER,
				topUniMulticastStormInPacketRate
					INTEGER,
				topUniMulticastStormOutPacketRate
					INTEGER,
				topUniBroadcastStormEnable
					INTEGER,
				topUniBroadcastStormInPacketRate
					INTEGER,
				topUniBroadcastStormOutPacketRate
					INTEGER
			 }

		-- 1.3.6.1.4.1.32285.11.2.3.5.2.1.1
		topUniBroadcastStormSuppressionCardIndex OBJECT-TYPE
			SYNTAX TopEPonSlotIndex
			MAX-ACCESS not-accessible
			STATUS current
			DESCRIPTION
				"Card Index
				The value of this cardIndex depends on onuType.
				fixed(1) - set to 0, to indicate slot num is meaningless.
				chassisBased(2) - MUST NOT be zero
				"
			::= { topUniBroadcastStormSuppressionEntry 1 }

		
		-- 1.3.6.1.4.1.32285.11.2.3.5.2.1.2
		topUniBroadcastStormSuppressionPonIndex OBJECT-TYPE
			SYNTAX TopEPonPonIndex
			MAX-ACCESS not-accessible
			STATUS current
			DESCRIPTION
				"Pon index"
			::= { topUniBroadcastStormSuppressionEntry 2 }

		
		-- 1.3.6.1.4.1.32285.11.2.3.5.2.1.3
		topUniBroadcastStormSuppressionOnuIndex OBJECT-TYPE
			SYNTAX TopEPonOnuAuthNum
			MAX-ACCESS not-accessible
			STATUS current
			DESCRIPTION
				"Pon index"
			::= { topUniBroadcastStormSuppressionEntry 3 }

		
		-- 1.3.6.1.4.1.32285.11.2.3.5.2.1.4
		topUniBroadcastStormSuppressionPortIndex OBJECT-TYPE
			SYNTAX TopEPonUniPortIndex
			MAX-ACCESS not-accessible
			STATUS current
			DESCRIPTION
				"Port Index"
			::= { topUniBroadcastStormSuppressionEntry 4 }

		
		-- 1.3.6.1.4.1.32285.11.2.3.5.2.1.5
		topUniUnicastStormEnable OBJECT-TYPE
			SYNTAX INTEGER
				{
				true(1),
				false(2)
				}
			MAX-ACCESS read-write
			STATUS current
			DESCRIPTION
				"Description."
			::= { topUniBroadcastStormSuppressionEntry 5 }

		
		-- 1.3.6.1.4.1.32285.11.2.3.5.2.1.6
		topUniUnicastStormInPacketRate OBJECT-TYPE
			SYNTAX INTEGER
			MAX-ACCESS read-write
			STATUS current
			DESCRIPTION
				"Description."
			::= { topUniBroadcastStormSuppressionEntry 6 }

		
		-- 1.3.6.1.4.1.32285.11.2.3.5.2.1.7
		topUniUnicastStormOutPacketRate OBJECT-TYPE
			SYNTAX INTEGER
			MAX-ACCESS read-write
			STATUS current
			DESCRIPTION
				"Description."
			::= { topUniBroadcastStormSuppressionEntry 7 }

		
		-- 1.3.6.1.4.1.32285.11.2.3.5.2.1.8
		topUniMulticastStormEnable OBJECT-TYPE
			SYNTAX INTEGER
				{
				true(1),
				false(2)
				}
			MAX-ACCESS read-write
			STATUS current
			DESCRIPTION
				"Description."
			::= { topUniBroadcastStormSuppressionEntry 8 }

		
		-- 1.3.6.1.4.1.32285.11.2.3.5.2.1.9
		topUniMulticastStormInPacketRate OBJECT-TYPE
			SYNTAX INTEGER
			MAX-ACCESS read-write
			STATUS current
			DESCRIPTION
				"Description."
			::= { topUniBroadcastStormSuppressionEntry 9 }

		
		-- 1.3.6.1.4.1.32285.11.2.3.5.2.1.10
		topUniMulticastStormOutPacketRate OBJECT-TYPE
			SYNTAX INTEGER
			MAX-ACCESS read-write
			STATUS current
			DESCRIPTION
				"Description."
			::= { topUniBroadcastStormSuppressionEntry 10 }

		
		-- 1.3.6.1.4.1.32285.11.2.3.5.2.1.11
		topUniBroadcastStormEnable OBJECT-TYPE
			SYNTAX INTEGER
				{
				true(1),
				false(2)
				}
			MAX-ACCESS read-write
			STATUS current
			DESCRIPTION
				"Description."
			::= { topUniBroadcastStormSuppressionEntry 11 }

		
		-- 1.3.6.1.4.1.32285.11.2.3.5.2.1.12
		topUniBroadcastStormInPacketRate OBJECT-TYPE
			SYNTAX INTEGER
			MAX-ACCESS read-write
			STATUS current
			DESCRIPTION
				"Description."
			::= { topUniBroadcastStormSuppressionEntry 12 }

		
		-- 1.3.6.1.4.1.32285.11.2.3.5.2.1.13
		topUniBroadcastStormOutPacketRate OBJECT-TYPE
			SYNTAX INTEGER
			MAX-ACCESS read-write
			STATUS current
			DESCRIPTION
				"Description."
			::= { topUniBroadcastStormSuppressionEntry 13 }

		
		-- 1.3.6.1.4.1.32285.11.2.3.6
		topIgmpMgmtObjects OBJECT IDENTIFIER ::= { topvisionEponTree 6 }

		
		-- 1.3.6.1.4.1.32285.11.2.3.6.1
		topMcOltConfigMgmtObjects OBJECT IDENTIFIER ::= { topIgmpMgmtObjects 1 }

		
		-- 1.3.6.1.4.1.32285.11.2.3.6.1.1
		topMcParamMgmtObjects OBJECT IDENTIFIER ::= { topMcOltConfigMgmtObjects 1 }

		
		-- 1.3.6.1.4.1.32285.11.2.3.6.1.1.1
		topMcMaxGroupNum OBJECT-TYPE
			SYNTAX INTEGER (1..2000)
			MAX-ACCESS read-write
			STATUS current
			DESCRIPTION
				"max multicast group quantity"
			DEFVAL { 2000 }
			::= { topMcParamMgmtObjects 1 }

		
		-- 1.3.6.1.4.1.32285.11.2.3.6.1.2
		topMcSniConfigMgmtObjects OBJECT IDENTIFIER ::= { topMcOltConfigMgmtObjects 2 }

		
		-- 1.3.6.1.4.1.32285.11.2.3.6.1.2.1
		topMcSniPortType OBJECT-TYPE
			SYNTAX INTEGER
				{
				anyPort(0),
				phyPort(1),
				aggPort(2)
				}
			MAX-ACCESS read-write
			STATUS current
			DESCRIPTION
				"config multicast uplink port type, one record only allow to exists.
				default value indicate that all uplinks ports will transit/receive
				igmp package, in case they have received such package."
			DEFVAL { 0 }
			::= { topMcSniConfigMgmtObjects 1 }

		
		-- 1.3.6.1.4.1.32285.11.2.3.6.1.2.2
		topMcSniPort OBJECT-TYPE
			SYNTAX OCTET STRING (SIZE (2))
			MAX-ACCESS read-write
			STATUS current
			DESCRIPTION
				"From MSB, the first octet is SLOT-INDEX, and then PORT-INDEX."
			::= { topMcSniConfigMgmtObjects 2 }

		
		-- 1.3.6.1.4.1.32285.11.2.3.6.1.2.3
		topMcSniAggPort OBJECT-TYPE
			SYNTAX INTEGER
			MAX-ACCESS read-write
			STATUS current
			DESCRIPTION
				"uplink Agg group id"
			::= { topMcSniConfigMgmtObjects 3 }

		
		-- 1.3.6.1.4.1.32285.11.2.3.6.1.2.4
		topMcSniAgingTime OBJECT-TYPE
			SYNTAX INTEGER (1..2000)
			UNITS "seconds"
			MAX-ACCESS read-write
			STATUS current
			DESCRIPTION
				"aging time, unit: seconds"
			DEFVAL { 250 }
			::= { topMcSniConfigMgmtObjects 4 }

		
		-- 1.3.6.1.4.1.32285.11.2.3.6.2
		topMcOnuConfigMgmtObjects OBJECT IDENTIFIER ::= { topIgmpMgmtObjects 2 }

		
		-- 1.3.6.1.4.1.32285.11.2.3.6.2.1
		topMcOnuParamMgmtObjects OBJECT IDENTIFIER ::= { topMcOnuConfigMgmtObjects 1 }

		
		-- 1.3.6.1.4.1.32285.11.2.3.6.2.1.1
		topMcOnuTable OBJECT-TYPE
			SYNTAX SEQUENCE OF TopMcOnuEntry
			MAX-ACCESS not-accessible
			STATUS current
			DESCRIPTION
				"ONU IGMP config table"
			::= { topMcOnuParamMgmtObjects 1 }

		
		-- 1.3.6.1.4.1.32285.11.2.3.6.2.1.1.1
		topMcOnuEntry OBJECT-TYPE
			SYNTAX TopMcOnuEntry
			MAX-ACCESS not-accessible
			STATUS current
			DESCRIPTION
				"The onuInfoEntry Information"
			INDEX { topMcOnuCardIndex, topMcOnuPonIndex, topMcOnuIndex }
			::= { topMcOnuTable 1 }

		
		TopMcOnuEntry ::=
			SEQUENCE { 
				topMcOnuCardIndex
					TopEPonSlotIndex,
				topMcOnuPonIndex
					TopEPonPonIndex,
				topMcOnuIndex
					TopEPonOnuAuthNum,
				topMcOnuMode
					INTEGER,
				topMcOnuFastLeave
					INTEGER
			 }

		-- 1.3.6.1.4.1.32285.11.2.3.6.2.1.1.1.1
		topMcOnuCardIndex OBJECT-TYPE
			SYNTAX TopEPonSlotIndex
			MAX-ACCESS not-accessible
			STATUS current
			DESCRIPTION
				"slot Index"
			::= { topMcOnuEntry 1 }

		
		-- 1.3.6.1.4.1.32285.11.2.3.6.2.1.1.1.2
		topMcOnuPonIndex OBJECT-TYPE
			SYNTAX TopEPonPonIndex
			MAX-ACCESS not-accessible
			STATUS current
			DESCRIPTION
				"pon Index"
			::= { topMcOnuEntry 2 }

		
		-- 1.3.6.1.4.1.32285.11.2.3.6.2.1.1.1.3
		topMcOnuIndex OBJECT-TYPE
			SYNTAX TopEPonOnuAuthNum
			MAX-ACCESS not-accessible
			STATUS current
			DESCRIPTION
				"ONU auth Index"
			::= { topMcOnuEntry 3 }

		
		-- 1.3.6.1.4.1.32285.11.2.3.6.2.1.1.1.4
		topMcOnuMode OBJECT-TYPE
			SYNTAX INTEGER
				{
				ctc(1),
				snooping(2),
				disable(3)
				}
			MAX-ACCESS read-write
			STATUS current
			DESCRIPTION
				"igmp mode, depend on igmpMode in igmpEntityEntry"
			DEFVAL { 3 }
			::= { topMcOnuEntry 4 }

		
		-- 1.3.6.1.4.1.32285.11.2.3.6.2.1.1.1.5
		topMcOnuFastLeave OBJECT-TYPE
			SYNTAX INTEGER
				{
				enable(1),
				disable(2)
				}
			MAX-ACCESS read-write
			STATUS current
			DESCRIPTION
				"onu fast leave"
			DEFVAL { 2 }
			::= { topMcOnuEntry 5 }

		
		-- 1.3.6.1.4.1.32285.11.2.3.6.2.1.2
		topMcOnuVlanTransTable OBJECT-TYPE
			SYNTAX SEQUENCE OF TopMcOnuVlanTransEntry
			MAX-ACCESS not-accessible
			STATUS current
			DESCRIPTION
				"MC vlan translation table"
			::= { topMcOnuParamMgmtObjects 2 }

		
		-- 1.3.6.1.4.1.32285.11.2.3.6.2.1.2.1
		topMcOnuVlanTransEntry OBJECT-TYPE
			SYNTAX TopMcOnuVlanTransEntry
			MAX-ACCESS not-accessible
			STATUS current
			DESCRIPTION
				"MC vlan translation Information"
			INDEX { topMcOnuVlanTransIndex }
			::= { topMcOnuVlanTransTable 1 }

		
		TopMcOnuVlanTransEntry ::=
			SEQUENCE { 
				topMcOnuVlanTransIndex
					INTEGER,
				topMcOnuVlanTransOldVidList
					OCTET STRING,
				topMcOnuVlanTransNewVidList
					OCTET STRING,
				topMcOnuVlanTransRowStatus
					RowStatus
			 }

		-- 1.3.6.1.4.1.32285.11.2.3.6.2.1.2.1.1
		topMcOnuVlanTransIndex OBJECT-TYPE
			SYNTAX INTEGER (1..64)
			MAX-ACCESS not-accessible
			STATUS current
			DESCRIPTION
				"translation index"
			::= { topMcOnuVlanTransEntry 1 }

		
		-- 1.3.6.1.4.1.32285.11.2.3.6.2.1.2.1.2
		topMcOnuVlanTransOldVidList OBJECT-TYPE
			SYNTAX OCTET STRING (SIZE (16))
			MAX-ACCESS read-create
			STATUS current
			DESCRIPTION
				"old vlan id array.every 2 bytes meaning a vid ,so the string consist of max 8 vid ."
			::= { topMcOnuVlanTransEntry 2 }

		
		-- 1.3.6.1.4.1.32285.11.2.3.6.2.1.2.1.3
		topMcOnuVlanTransNewVidList OBJECT-TYPE
			SYNTAX OCTET STRING (SIZE (16))
			MAX-ACCESS read-create
			STATUS current
			DESCRIPTION
				"vid after translation.every 2 bytes meaning a vid ,so the string consist of max 8 vid ,
				 and every vid  is corresponding with the same position from the topMcOnuVlanTransOldVidList!"
			::= { topMcOnuVlanTransEntry 3 }

		
		-- 1.3.6.1.4.1.32285.11.2.3.6.2.1.2.1.4
		topMcOnuVlanTransRowStatus OBJECT-TYPE
			SYNTAX RowStatus
			MAX-ACCESS read-create
			STATUS current
			DESCRIPTION
				"add/del/set"
			::= { topMcOnuVlanTransEntry 4 }

		
		-- 1.3.6.1.4.1.32285.11.2.3.6.2.2
		topMcUniConfigMgmtObjects OBJECT IDENTIFIER ::= { topMcOnuConfigMgmtObjects 2 }

		
		-- 1.3.6.1.4.1.32285.11.2.3.6.2.2.1
		topMcUniConfigTable OBJECT-TYPE
			SYNTAX SEQUENCE OF TopMcUniConfigEntry
			MAX-ACCESS not-accessible
			STATUS current
			DESCRIPTION
				"ONU IGMP config table"
			::= { topMcUniConfigMgmtObjects 1 }

		
		-- 1.3.6.1.4.1.32285.11.2.3.6.2.2.1.1
		topMcUniConfigEntry OBJECT-TYPE
			SYNTAX TopMcUniConfigEntry
			MAX-ACCESS not-accessible
			STATUS current
			DESCRIPTION
				"The onuInfoEntry Information"
			INDEX { topMcUniCardIndex, topMcUniPonIndex, topMcUniOnuAuthIndex, topMcUniIndex }
			::= { topMcUniConfigTable 1 }

		
		TopMcUniConfigEntry ::=
			SEQUENCE { 
				topMcUniCardIndex
					TopEPonSlotIndex,
				topMcUniPonIndex
					TopEPonPonIndex,
				topMcUniOnuAuthIndex
					TopEPonOnuAuthNum,
				topMcUniIndex
					TopEPonUniPortIndex,
				topMcUniMaxGroupQuantity
					INTEGER,
				topMcUniVlanMode
					INTEGER,
				topMcUniVlanTransIdx
					INTEGER,
				topMcUniVlanList
					OCTET STRING
			 }

		-- 1.3.6.1.4.1.32285.11.2.3.6.2.2.1.1.1
		topMcUniCardIndex OBJECT-TYPE
			SYNTAX TopEPonSlotIndex
			MAX-ACCESS not-accessible
			STATUS current
			DESCRIPTION
				"slot Index"
			::= { topMcUniConfigEntry 1 }

		
		-- 1.3.6.1.4.1.32285.11.2.3.6.2.2.1.1.2
		topMcUniPonIndex OBJECT-TYPE
			SYNTAX TopEPonPonIndex
			MAX-ACCESS not-accessible
			STATUS current
			DESCRIPTION
				"pon Index"
			::= { topMcUniConfigEntry 2 }

		
		-- 1.3.6.1.4.1.32285.11.2.3.6.2.2.1.1.3
		topMcUniOnuAuthIndex OBJECT-TYPE
			SYNTAX TopEPonOnuAuthNum
			MAX-ACCESS not-accessible
			STATUS current
			DESCRIPTION
				"ONU auth Index"
			::= { topMcUniConfigEntry 3 }

		
		-- 1.3.6.1.4.1.32285.11.2.3.6.2.2.1.1.4
		topMcUniIndex OBJECT-TYPE
			SYNTAX TopEPonUniPortIndex
			MAX-ACCESS not-accessible
			STATUS current
			DESCRIPTION
				"uni port Index"
			::= { topMcUniConfigEntry 4 }

		
		-- 1.3.6.1.4.1.32285.11.2.3.6.2.2.1.1.5
		topMcUniMaxGroupQuantity OBJECT-TYPE
			SYNTAX INTEGER (0..64)
			MAX-ACCESS read-write
			STATUS current
			DESCRIPTION
				"0: do not limit
				other value: use specific value"
			DEFVAL { 4 }
			::= { topMcUniConfigEntry 5 }

		
		-- 1.3.6.1.4.1.32285.11.2.3.6.2.2.1.1.6
		topMcUniVlanMode OBJECT-TYPE
			SYNTAX INTEGER
				{
				strip(1),
				translation(2),
				keep(3)
				}
			MAX-ACCESS read-write
			STATUS current
			DESCRIPTION
				"onu uni mc vlan mode"
			DEFVAL { 1 }
			::= { topMcUniConfigEntry 6 }

		
		-- 1.3.6.1.4.1.32285.11.2.3.6.2.2.1.1.7
		topMcUniVlanTransIdx OBJECT-TYPE
			SYNTAX INTEGER (1..64)
			MAX-ACCESS read-write
			STATUS current
			DESCRIPTION
				"vlan translation map index.
				Valid only when topMcUniVlanMode is translation(2)."
			::= { topMcUniConfigEntry 7 }

		
		-- 1.3.6.1.4.1.32285.11.2.3.6.2.2.1.1.8
		topMcUniVlanList OBJECT-TYPE
			SYNTAX OCTET STRING (SIZE (128))
			MAX-ACCESS read-write
			STATUS current
			DESCRIPTION
				"Uni Port allows max 64 multicast vlans.
				Every two octets compose an integer, which represent an vlan id."
			::= { topMcUniConfigEntry 8 }

		
		-- 1.3.6.1.4.1.32285.11.2.3.6.3
		topControlledMcMgmtObjects OBJECT IDENTIFIER ::= { topIgmpMgmtObjects 3 }

		
		-- 1.3.6.1.4.1.32285.11.2.3.6.3.1
		topControlledMcCdrTable OBJECT-TYPE
			SYNTAX SEQUENCE OF TopControlledMcCdrEntry
			MAX-ACCESS not-accessible
			STATUS current
			DESCRIPTION
				"Table that contains information of CDRs."
			::= { topControlledMcMgmtObjects 1 }

		
		-- 1.3.6.1.4.1.32285.11.2.3.6.3.1.1
		topControlledMcCdrEntry OBJECT-TYPE
			SYNTAX TopControlledMcCdrEntry
			MAX-ACCESS not-accessible
			STATUS current
			DESCRIPTION
				"An entry in the eponOltCdrTable containing information
				of each CDR. It is indexed by topControllededMcSequenceIndex."
			INDEX { topControlledMcSequenceIndex }
			::= { topControlledMcCdrTable 1 }

		
		TopControlledMcCdrEntry ::=
			SEQUENCE { 
				topControlledMcSequenceIndex
					INTEGER,
				topControlledMcCdrSlotNum
					TopEPonSlotIndex,
				topControlledMcCdrPonNum
					TopEPonPonIndex,
				topControlledMcCdrOnuAuthNum
					TopEPonOnuAuthNum,
				topControlledMcCdrUniNum
					TopEPonUniPortIndex,
				topControlledMcCdrIgmpReqType
					INTEGER,
				topControlledMcCdrIgmpReqTime
					TimeStamp,
				topControlledMcCdrIgmpReqChannel
					IpAddress,
				topControlledMcCdrIgmpReqRight
					INTEGER,
				topControlledMcCdrIgmpReqResult
					INTEGER,
				topControlledMcCdrLeaveType
					INTEGER,
				topControlledMcCdrRecordTime
					TimeStamp
			 }

		-- 1.3.6.1.4.1.32285.11.2.3.6.3.1.1.1
		topControlledMcSequenceIndex OBJECT-TYPE
			SYNTAX INTEGER
			MAX-ACCESS not-accessible
			STATUS current
			DESCRIPTION
				"The sequence number of this CDR, used as the index into eponOltCdrTable."
			::= { topControlledMcCdrEntry 1 }

		
		-- 1.3.6.1.4.1.32285.11.2.3.6.3.1.1.2
		topControlledMcCdrSlotNum OBJECT-TYPE
			SYNTAX TopEPonSlotIndex
			MAX-ACCESS read-only
			STATUS current
			DESCRIPTION
				"Decide which UNI this CDR was created for, in conjunction with topControllededMcCdrPonNum,
				topControllededMcCdrOnuAuthNum and topControllededMcCdrUniNum."
			::= { topControlledMcCdrEntry 2 }

		
		-- 1.3.6.1.4.1.32285.11.2.3.6.3.1.1.3
		topControlledMcCdrPonNum OBJECT-TYPE
			SYNTAX TopEPonPonIndex
			MAX-ACCESS read-only
			STATUS current
			DESCRIPTION
				"Decide which UNI this CDR was created for, in conjunction with topControllededMcCdrSlotNum,
				topControllededMcCdrOnuAuthNum and topControllededMcCdrUniNum."
			::= { topControlledMcCdrEntry 3 }

		
		-- 1.3.6.1.4.1.32285.11.2.3.6.3.1.1.4
		topControlledMcCdrOnuAuthNum OBJECT-TYPE
			SYNTAX TopEPonOnuAuthNum
			MAX-ACCESS read-only
			STATUS current
			DESCRIPTION
				"Decide which UNI this CDR was created for, in conjunction with topControllededMcCdrSlotNum,
				topControllededMcCdrPonNum and topControllededMcCdrUniNum."
			::= { topControlledMcCdrEntry 4 }

		
		-- 1.3.6.1.4.1.32285.11.2.3.6.3.1.1.5
		topControlledMcCdrUniNum OBJECT-TYPE
			SYNTAX TopEPonUniPortIndex
			MAX-ACCESS read-only
			STATUS current
			DESCRIPTION
				"Decide which UNI this CDR was created for, in conjunction with topControllededMcCdrSlotNum,
				topControllededMcCdrPonNum and topControllededMcCdrOnuAuthNum."
			::= { topControlledMcCdrEntry 5 }

		
		-- 1.3.6.1.4.1.32285.11.2.3.6.3.1.1.6
		topControlledMcCdrIgmpReqType OBJECT-TYPE
			SYNTAX INTEGER
				{
				join(0),
				leave(1)
				}
			MAX-ACCESS read-only
			STATUS current
			DESCRIPTION
				"Type of the IGMP request message sent by the corresponding UNI."
			::= { topControlledMcCdrEntry 6 }

		
		-- 1.3.6.1.4.1.32285.11.2.3.6.3.1.1.7
		topControlledMcCdrIgmpReqTime OBJECT-TYPE
			SYNTAX TimeStamp
			MAX-ACCESS read-only
			STATUS current
			DESCRIPTION
				"This object indicates when the Igmp request message was sent."
			::= { topControlledMcCdrEntry 7 }

		
		-- 1.3.6.1.4.1.32285.11.2.3.6.3.1.1.8
		topControlledMcCdrIgmpReqChannel OBJECT-TYPE
			SYNTAX IpAddress
			MAX-ACCESS read-only
			STATUS current
			DESCRIPTION
				"This object indicates which channel the Igmp request message was sent for."
			::= { topControlledMcCdrEntry 8 }

		
		-- 1.3.6.1.4.1.32285.11.2.3.6.3.1.1.9
		topControlledMcCdrIgmpReqRight OBJECT-TYPE
			SYNTAX INTEGER
				{
				deny(0),
				permit(1),
				preview(2)
				}
			MAX-ACCESS read-only
			STATUS current
			DESCRIPTION
				"This object indicates what access that the UNI has, to the channel the Igmp
				request message was sent for."
			::= { topControlledMcCdrEntry 9 }

		
		-- 1.3.6.1.4.1.32285.11.2.3.6.3.1.1.10
		topControlledMcCdrIgmpReqResult OBJECT-TYPE
			SYNTAX INTEGER
				{
				success(0),
				failure(1)
				}
			MAX-ACCESS read-only
			STATUS current
			DESCRIPTION
				"Rusult of the request, success or failure."
			::= { topControlledMcCdrEntry 10 }

		
		-- 1.3.6.1.4.1.32285.11.2.3.6.3.1.1.11
		topControlledMcCdrLeaveType OBJECT-TYPE
			SYNTAX INTEGER
				{
				selfLeaving(0),
				forceLeaving(1)
				}
			MAX-ACCESS read-only
			STATUS current
			DESCRIPTION
				"The cause of UNI's leave, self-request or being kicked."
			::= { topControlledMcCdrEntry 11 }

		
		-- 1.3.6.1.4.1.32285.11.2.3.6.3.1.1.12
		topControlledMcCdrRecordTime OBJECT-TYPE
			SYNTAX TimeStamp
			MAX-ACCESS read-only
			STATUS current
			DESCRIPTION
				"This object indicates when the CDR was created."
			::= { topControlledMcCdrEntry 12 }

		
		-- 1.3.6.1.4.1.32285.11.2.3.6.3.2
		topControlledMcPreviewIntervalTable OBJECT-TYPE
			SYNTAX SEQUENCE OF TopControlledMcPreviewIntervalEntry
			MAX-ACCESS not-accessible
			STATUS current
			DESCRIPTION
				"topControlledMcPreviewIntervalTable"
			::= { topControlledMcMgmtObjects 2 }

		
		-- 1.3.6.1.4.1.32285.11.2.3.6.3.2.1
		topControlledMcPreviewIntervalEntry OBJECT-TYPE
			SYNTAX TopControlledMcPreviewIntervalEntry
			MAX-ACCESS not-accessible
			STATUS current
			DESCRIPTION
				"ControlledMcPreviewIntervalEntry."
			INDEX { topControlledMcPreCmIndex }
			::= { topControlledMcPreviewIntervalTable 1 }

		
		TopControlledMcPreviewIntervalEntry ::=
			SEQUENCE { 
				topControlledMcPreCmIndex
					INTEGER,
				topControlledMcPreviewInterval
					INTEGER
			 }

		-- 1.3.6.1.4.1.32285.11.2.3.6.3.2.1.1
		topControlledMcPreCmIndex OBJECT-TYPE
			SYNTAX INTEGER (1..2000)
			MAX-ACCESS not-accessible
			STATUS current
			DESCRIPTION
				"Controlled igmp cm index."
			::= { topControlledMcPreviewIntervalEntry 1 }

		
		-- 1.3.6.1.4.1.32285.11.2.3.6.3.2.1.2
		topControlledMcPreviewInterval OBJECT-TYPE
			SYNTAX INTEGER (30..60)
			MAX-ACCESS read-write
			STATUS current
			DESCRIPTION
				"IGMP previewInterval, this is a node of controlledMulticastPackageTable. If you want to
				operate this node, you should make sure data is already in controlledMulticastPackageTable!"
			DEFVAL { 60 }
			::= { topControlledMcPreviewIntervalEntry 2 }

		
		-- 1.3.6.1.4.1.32285.11.2.3.6.4
		topMcForwardingMgmtObjects OBJECT IDENTIFIER ::= { topIgmpMgmtObjects 4 }

		
		-- 1.3.6.1.4.1.32285.11.2.3.6.4.1
		topMcForwardingSlotTable OBJECT-TYPE
			SYNTAX SEQUENCE OF TopMcForwardingSlotEntry
			MAX-ACCESS not-accessible
			STATUS current
			DESCRIPTION
				"IGMP forwarding slot table."
			::= { topMcForwardingMgmtObjects 1 }

		
		-- 1.3.6.1.4.1.32285.11.2.3.6.4.1.1
		topMcForwardingSlotEntry OBJECT-TYPE
			SYNTAX TopMcForwardingSlotEntry
			MAX-ACCESS not-accessible
			STATUS current
			DESCRIPTION
				"IGMP forwarding slot table entry."
			INDEX { topMcForwardingSlotGroupIdIndex }
			::= { topMcForwardingSlotTable 1 }

		
		TopMcForwardingSlotEntry ::=
			SEQUENCE { 
				topMcForwardingSlotGroupIdIndex
					INTEGER,
				topMcForwardingSlotCount
					INTEGER,
				topMcForwardingSlotList
					INTEGER
			 }

		-- 1.3.6.1.4.1.32285.11.2.3.6.4.1.1.1
		topMcForwardingSlotGroupIdIndex OBJECT-TYPE
			SYNTAX INTEGER (1..2000)
			MAX-ACCESS not-accessible
			STATUS current
			DESCRIPTION
				"IGMP group index."
			::= { topMcForwardingSlotEntry 1 }

		
		-- 1.3.6.1.4.1.32285.11.2.3.6.4.1.1.2
		topMcForwardingSlotCount OBJECT-TYPE
			SYNTAX INTEGER
			MAX-ACCESS read-only
			STATUS current
			DESCRIPTION
				"Slot count."
			::= { topMcForwardingSlotEntry 2 }

		-- 1.3.6.1.4.1.32285.11.2.3.6.4.1.1.3
		topMcForwardingSlotList OBJECT-TYPE
			SYNTAX INTEGER
			MAX-ACCESS read-only
			STATUS current
			DESCRIPTION
				"Slot list, infact it is bitmap."
			::= { topMcForwardingSlotEntry 3 }

		
		-- 1.3.6.1.4.1.32285.11.2.3.6.4.2
		topMcForwardingPortTable OBJECT-TYPE
			SYNTAX SEQUENCE OF TopMcForwardingPortEntry
			MAX-ACCESS not-accessible
			STATUS current
			DESCRIPTION
				"IGMP forwarding port table."
			::= { topMcForwardingMgmtObjects 2 }

		
		-- 1.3.6.1.4.1.32285.11.2.3.6.4.2.1
		topMcForwardingPortEntry OBJECT-TYPE
			SYNTAX TopMcForwardingPortEntry
			MAX-ACCESS not-accessible
			STATUS current
			DESCRIPTION
				"IGMP forwarding port table entry."
			INDEX { topMcForwardingPortGroupIdIndex, topMcForwardingPortSlotIndex }
			::= { topMcForwardingPortTable 1 }

		
		TopMcForwardingPortEntry ::=
			SEQUENCE { 
				topMcForwardingPortGroupIdIndex
					INTEGER,
				topMcForwardingPortSlotIndex
					TopEPonSlotIndex,
				topMcForwardingPortCount
					INTEGER,
				topMcForwardingPortList
					INTEGER
			 }

		-- 1.3.6.1.4.1.32285.11.2.3.6.4.2.1.1
		topMcForwardingPortGroupIdIndex OBJECT-TYPE
			SYNTAX INTEGER (1..2000)
			MAX-ACCESS not-accessible
			STATUS current
			DESCRIPTION
				"IGMP group index."
			::= { topMcForwardingPortEntry 1 }

		
		-- 1.3.6.1.4.1.32285.11.2.3.6.4.2.1.2
		topMcForwardingPortSlotIndex OBJECT-TYPE
			SYNTAX TopEPonSlotIndex
			MAX-ACCESS not-accessible
			STATUS current
			DESCRIPTION
				"IGMP group slot index."
			::= { topMcForwardingPortEntry 2 }

		
		-- 1.3.6.1.4.1.32285.11.2.3.6.4.2.1.3
		topMcForwardingPortCount OBJECT-TYPE
			SYNTAX INTEGER
			MAX-ACCESS read-only
			STATUS current
			DESCRIPTION
				"IGMP port count,"
			::= { topMcForwardingPortEntry 3 }

		-- 1.3.6.1.4.1.32285.11.2.3.6.4.2.1.4
		topMcForwardingPortList OBJECT-TYPE
			SYNTAX INTEGER
			MAX-ACCESS read-only
			STATUS current
			DESCRIPTION
				"IGMP forwarding port bitmap."
			::= { topMcForwardingPortEntry 4 }

		
		-- 1.3.6.1.4.1.32285.11.2.3.6.4.3
		topMcForwardingOnuTable OBJECT-TYPE
			SYNTAX SEQUENCE OF TopMcForwardingOnuEntry
			MAX-ACCESS not-accessible
			STATUS current
			DESCRIPTION
				"IGMP forwarding onu table."
			::= { topMcForwardingMgmtObjects 3 }

		
		-- 1.3.6.1.4.1.32285.11.2.3.6.4.3.1
		topMcForwardingOnuEntry OBJECT-TYPE
			SYNTAX TopMcForwardingOnuEntry
			MAX-ACCESS not-accessible
			STATUS current
			DESCRIPTION
				"IGMP forwarding onu table entry."
			INDEX { topMcForwardingOnuGroupIdIndex, topMcForwardingOnuSlotIndex, topMcForwardingOnuPortIndex }
			::= { topMcForwardingOnuTable 1 }

		
		TopMcForwardingOnuEntry ::=
			SEQUENCE { 
				topMcForwardingOnuGroupIdIndex
					INTEGER,
				topMcForwardingOnuSlotIndex
					TopEPonSlotIndex,
				topMcForwardingOnuPortIndex
					TopEPonPonIndex,
				topMcForwardingOnuCount
					INTEGER,
				topMcForwardingOnuList
					OCTET STRING
			 }

		-- 1.3.6.1.4.1.32285.11.2.3.6.4.3.1.1
		topMcForwardingOnuGroupIdIndex OBJECT-TYPE
			SYNTAX INTEGER (1..2000)
			MAX-ACCESS not-accessible
			STATUS current
			DESCRIPTION
				"IGMP group index."
			::= { topMcForwardingOnuEntry 1 }

		
		-- 1.3.6.1.4.1.32285.11.2.3.6.4.3.1.2
		topMcForwardingOnuSlotIndex OBJECT-TYPE
			SYNTAX TopEPonSlotIndex
			MAX-ACCESS not-accessible
			STATUS current
			DESCRIPTION
				"IGMP slot index."
			::= { topMcForwardingOnuEntry 2 }

		
		-- 1.3.6.1.4.1.32285.11.2.3.6.4.3.1.3
		topMcForwardingOnuPortIndex OBJECT-TYPE
			SYNTAX TopEPonPonIndex
			MAX-ACCESS not-accessible
			STATUS current
			DESCRIPTION
				"IGMP port index."
			::= { topMcForwardingOnuEntry 3 }

		
		-- 1.3.6.1.4.1.32285.11.2.3.6.4.3.1.4
		topMcForwardingOnuCount OBJECT-TYPE
			SYNTAX INTEGER
			MAX-ACCESS read-only
			STATUS current
			DESCRIPTION
				"IGMP onu count."
			::= { topMcForwardingOnuEntry 4 }

		
		-- 1.3.6.1.4.1.32285.11.2.3.6.4.3.1.5
		topMcForwardingOnuList OBJECT-TYPE
			SYNTAX OCTET STRING (SIZE (640))
			MAX-ACCESS read-only
			STATUS current
			DESCRIPTION
				"IGMP onu bitmap or uni bitmap. 5 bytes to descript an onu, the first byte is ID of this onu,
				the other 4 bytes descript this onu uni bitmap. If the igmp type is proxy, No uni bitmap,so the
				last 4 bytes is 0, if the type is CTC, the 4 bytes contains uni bitmap information"
			::= { topMcForwardingOnuEntry 5 }

			
		-- 1.3.6.1.4.1.32285.11.2.3.7
		topVlanMgmtObjects OBJECT IDENTIFIER ::= { topvisionEponTree 7 }

		
		-- 1.3.6.1.4.1.32285.11.2.3.7.1
		topLlidVlanGroup OBJECT-IDENTITY
			STATUS current
			DESCRIPTION 
				"llid-based vlan management."
			::= { topVlanMgmtObjects 1 }

		
		-- 1.3.6.1.4.1.32285.11.2.3.7.1.1
		topLlidVlanTransTable OBJECT-TYPE
			SYNTAX SEQUENCE OF TopLlidVlanTransEntry
			MAX-ACCESS not-accessible
			STATUS current
			DESCRIPTION
				"LLID, identify with ONU MAC"
			::= { topLlidVlanGroup 1 }

		
		-- 1.3.6.1.4.1.32285.11.2.3.7.1.1.1
		topLlidVlanTransEntry OBJECT-TYPE
			SYNTAX TopLlidVlanTransEntry
			MAX-ACCESS not-accessible
			STATUS current
			DESCRIPTION
				"llid-based vlan translation entry "
			INDEX { topLlidTransCardIdx, topLlidTransPonIdx, topLlidTransDevMac,topLlidTransVidIdx  }
			::= { topLlidVlanTransTable 1 }

		
		TopLlidVlanTransEntry ::=
			SEQUENCE { 
				topLlidTransCardIdx
					TopEPonSlotIndex,
				topLlidTransPonIdx
					TopEPonPonIndex,
				topLlidTransDevMac
					MacAddress,
				topLlidTransVidIdx
					INTEGER,
				topLlidTransNewVid
					INTEGER,
				topLlidTransCosMode
					INTEGER,
				topLlidTransNewCos
					INTEGER,
				topLlidTransNewTpid
					INTEGER,
				topLlidTransRowStatus
					RowStatus
			 }

		-- 1.3.6.1.4.1.32285.11.2.3.7.1.1.1.1
		topLlidTransCardIdx OBJECT-TYPE
			SYNTAX TopEPonSlotIndex
			MAX-ACCESS not-accessible
			STATUS current
			DESCRIPTION
				"slot index"
			::= { topLlidVlanTransEntry 1 }

		
		-- 1.3.6.1.4.1.32285.11.2.3.7.1.1.1.2
		topLlidTransPonIdx OBJECT-TYPE
			SYNTAX TopEPonPonIndex
			MAX-ACCESS not-accessible
			STATUS current
			DESCRIPTION
				"pon index"
			::= { topLlidVlanTransEntry 2 }

		
		-- 1.3.6.1.4.1.32285.11.2.3.7.1.1.1.3
		topLlidTransDevMac OBJECT-TYPE
			SYNTAX MacAddress
			MAX-ACCESS not-accessible
			STATUS current
			DESCRIPTION
				"ONU MAC"
			::= { topLlidVlanTransEntry 3 }

		
		-- 1.3.6.1.4.1.32285.11.2.3.7.1.1.1.4
		topLlidTransVidIdx OBJECT-TYPE
			SYNTAX INTEGER (1..4094)
			MAX-ACCESS not-accessible
			STATUS current
			DESCRIPTION
				"VLAN ID"
			::= { topLlidVlanTransEntry 4 }

		
		-- 1.3.6.1.4.1.32285.11.2.3.7.1.1.1.5
		topLlidTransNewVid OBJECT-TYPE
			SYNTAX INTEGER (1..4094)
			MAX-ACCESS read-create
			STATUS current
			DESCRIPTION
				"tvlan"
			::= { topLlidVlanTransEntry 5 }

		
		-- 1.3.6.1.4.1.32285.11.2.3.7.1.1.1.6
		topLlidTransCosMode OBJECT-TYPE
			SYNTAX INTEGER
				{
				remark(1),
				keepCos(2)
				}
			MAX-ACCESS read-create
			STATUS current
			DESCRIPTION
				"keepCos(2)-keep the current CoS.
				remark(1)-change Cos as per variable topLlidTransNewCos"
			DEFVAL { 2 }
			::= { topLlidVlanTransEntry 6 }

		
		-- 1.3.6.1.4.1.32285.11.2.3.7.1.1.1.7
		topLlidTransNewCos OBJECT-TYPE
			SYNTAX INTEGER (0..7)
			MAX-ACCESS read-create
			STATUS current
			DESCRIPTION
				"in case topLlidTransCosMode is remark(1),
				set new cos value"
			DEFVAL { 0 }
			::= { topLlidVlanTransEntry 7 }

		
		-- 1.3.6.1.4.1.32285.11.2.3.7.1.1.1.8
		topLlidTransNewTpid OBJECT-TYPE
			SYNTAX INTEGER (1..65535)
			MAX-ACCESS read-create
			STATUS current
			DESCRIPTION
				"value 0xFFFF means not to change the current TPID,
				otherwise modify it into this value."
			DEFVAL { '8100'h }
			::= { topLlidVlanTransEntry 8 }

		
		-- 1.3.6.1.4.1.32285.11.2.3.7.1.1.1.9
		topLlidTransRowStatus OBJECT-TYPE
			SYNTAX RowStatus
			MAX-ACCESS read-create
			STATUS current
			DESCRIPTION
				"add/del/set"
			::= { topLlidVlanTransEntry 9 }

		
		-- 1.3.6.1.4.1.32285.11.2.3.7.1.2
		topLlidVlanAggTable OBJECT-TYPE
			SYNTAX SEQUENCE OF TopLlidVlanAggEntry
			MAX-ACCESS not-accessible
			STATUS current
			DESCRIPTION
				"vlan based on llid aggregation."
			::= { topLlidVlanGroup 2 }

		
		-- 1.3.6.1.4.1.32285.11.2.3.7.1.2.1
		topLlidVlanAggEntry OBJECT-TYPE
			SYNTAX TopLlidVlanAggEntry
			MAX-ACCESS not-accessible
			STATUS current
			DESCRIPTION
				"vlan based on llid aggregation entry"
			INDEX { llidVlanAggCardIndex, llidVlanAggPonIndex, llidVlanAggMacAddr, llidVlanAfterAggVid }
			::= { topLlidVlanAggTable 1 }

		
		TopLlidVlanAggEntry ::=
			SEQUENCE { 
				llidVlanAggCardIndex
					TopEPonSlotIndex,
				llidVlanAggPonIndex
					TopEPonPonIndex,
				llidVlanAggMacAddr
					MacAddress,
				llidVlanAfterAggVid
					INTEGER,
				llidVlanBeforeAggVidList
					OCTET STRING,
				llidVlanAggCosMode
					INTEGER,
				llidVlanAggNewCos
					INTEGER,
				llidVlanAggNewTpid
					INTEGER,
				llidVlanAggRowStatus
					RowStatus
			 }

		-- 1.3.6.1.4.1.32285.11.2.3.7.1.2.1.1
		llidVlanAggCardIndex OBJECT-TYPE
			SYNTAX TopEPonSlotIndex
			MAX-ACCESS not-accessible
			STATUS current
			DESCRIPTION
				"Slot index"
			::= { topLlidVlanAggEntry 1 }

		
		-- 1.3.6.1.4.1.32285.11.2.3.7.1.2.1.2
		llidVlanAggPonIndex OBJECT-TYPE
			SYNTAX TopEPonPonIndex
			MAX-ACCESS not-accessible
			STATUS current
			DESCRIPTION
				"pon index"
			::= { topLlidVlanAggEntry 2 }

		
		-- 1.3.6.1.4.1.32285.11.2.3.7.1.2.1.3
		llidVlanAggMacAddr OBJECT-TYPE
			SYNTAX MacAddress
			MAX-ACCESS not-accessible
			STATUS current
			DESCRIPTION
				"ONU MAC"
			::= { topLlidVlanAggEntry 3 }

		
		-- 1.3.6.1.4.1.32285.11.2.3.7.1.2.1.4
		llidVlanAfterAggVid OBJECT-TYPE
			SYNTAX INTEGER (1..4094)
			MAX-ACCESS not-accessible
			STATUS current
			DESCRIPTION
				"vlan id"
			::= { topLlidVlanAggEntry 4 }

		
		-- 1.3.6.1.4.1.32285.11.2.3.7.1.2.1.5
		llidVlanBeforeAggVidList OBJECT-TYPE
			SYNTAX OCTET STRING (SIZE (512))
			MAX-ACCESS read-create
			STATUS current
			DESCRIPTION
				"vlan id"
			::= { topLlidVlanAggEntry 5 }

		
		-- 1.3.6.1.4.1.32285.11.2.3.7.1.2.1.6
		llidVlanAggCosMode OBJECT-TYPE
			SYNTAX INTEGER
				{
				remark(1),
				keepCos(2)
				}
			MAX-ACCESS read-create
			STATUS current
			DESCRIPTION
				"keepCos(2)-keep the current CoS.
				remark(1)-change Cos as per variable topLlidCosTransNewCos"
			DEFVAL { 2 }
			::= { topLlidVlanAggEntry 6 }

		
		-- 1.3.6.1.4.1.32285.11.2.3.7.1.2.1.7
		llidVlanAggNewCos OBJECT-TYPE
			SYNTAX INTEGER (0..7)
			MAX-ACCESS read-create
			STATUS current
			DESCRIPTION
				"in case topLlidCosTransCosMode is remark(1),
				set new cos value"
			DEFVAL { 0 }
			::= { topLlidVlanAggEntry 7 }

		
		-- 1.3.6.1.4.1.32285.11.2.3.7.1.2.1.8
		llidVlanAggNewTpid OBJECT-TYPE
			SYNTAX INTEGER (0..65535)
			MAX-ACCESS read-create
			STATUS current
			DESCRIPTION
				"value 0xFFFF means not to change the current TPID,
				otherwise modify it into this value."
			DEFVAL { '8100'h }
			::= { topLlidVlanAggEntry 8 }

		
		-- 1.3.6.1.4.1.32285.11.2.3.7.1.2.1.9
		llidVlanAggRowStatus OBJECT-TYPE
			SYNTAX RowStatus
			MAX-ACCESS read-create
			STATUS current
			DESCRIPTION
				"add/del/set"
			::= { topLlidVlanAggEntry 9 }

		
		-- 1.3.6.1.4.1.32285.11.2.3.7.1.3
		topLlidVlanTrunkTable OBJECT-TYPE
			SYNTAX SEQUENCE OF TopLlidVlanTrunkEntry
			MAX-ACCESS not-accessible
			STATUS current
			DESCRIPTION
				"Vlan trunk based on LLID only"
			::= { topLlidVlanGroup 3 }

		
		-- 1.3.6.1.4.1.32285.11.2.3.7.1.3.1
		topLlidVlanTrunkEntry OBJECT-TYPE
			SYNTAX TopLlidVlanTrunkEntry
			MAX-ACCESS not-accessible
			STATUS current
			DESCRIPTION
				"Vlan trunk based on LLID entry"
			INDEX { llidVlanTrunkCardIndex, llidVlanTrunkPonIndex, llidVlanTrunkMacIdx }
			::= { topLlidVlanTrunkTable 1 }

		
		TopLlidVlanTrunkEntry ::=
			SEQUENCE { 
				llidVlanTrunkCardIndex
					TopEPonSlotIndex,
				llidVlanTrunkPonIndex
					TopEPonPonIndex,
				llidVlanTrunkMacIdx
					MacAddress,
				llidVlanTrunkVidBmp
					OCTET STRING,
				llidVlanTrunkRowStatus
					RowStatus
			 }

		-- 1.3.6.1.4.1.32285.11.2.3.7.1.3.1.1
		llidVlanTrunkCardIndex OBJECT-TYPE
			SYNTAX TopEPonSlotIndex
			MAX-ACCESS not-accessible
			STATUS current
			DESCRIPTION
				"slot index"
			::= { topLlidVlanTrunkEntry 1 }

		
		-- 1.3.6.1.4.1.32285.11.2.3.7.1.3.1.2
		llidVlanTrunkPonIndex OBJECT-TYPE
			SYNTAX TopEPonPonIndex
			MAX-ACCESS not-accessible
			STATUS current
			DESCRIPTION
				"pon index"
			::= { topLlidVlanTrunkEntry 2 }

		
		-- 1.3.6.1.4.1.32285.11.2.3.7.1.3.1.3
		llidVlanTrunkMacIdx OBJECT-TYPE
			SYNTAX MacAddress
			MAX-ACCESS not-accessible
			STATUS current
			DESCRIPTION
				"MAC address"
			::= { topLlidVlanTrunkEntry 3 }

		
		-- 1.3.6.1.4.1.32285.11.2.3.7.1.3.1.4
		llidVlanTrunkVidBmp OBJECT-TYPE
			SYNTAX OCTET STRING (SIZE (512))
			MAX-ACCESS read-create
			STATUS current
			DESCRIPTION
				"Trunked Vlan List for the port
				INTERNETOCTETOCTET 0, OCTET 1, ...
				OCTETbitbit0bit1...bit7
				bitOCTETbitVLANVLAN ID0..4095
				bitVLAN 0,bitVLAN 4095
				bit"
			::= { topLlidVlanTrunkEntry 4 }

		
		-- 1.3.6.1.4.1.32285.11.2.3.7.1.3.1.5
		llidVlanTrunkRowStatus OBJECT-TYPE
			SYNTAX RowStatus
			MAX-ACCESS read-create
			STATUS current
			DESCRIPTION
				"add/del/set"
			::= { topLlidVlanTrunkEntry 5 }

		
		-- 1.3.6.1.4.1.32285.11.2.3.7.2
		topLlidQinQConfigGroup OBJECT-IDENTITY
			STATUS current
			DESCRIPTION 
				"llid-based vlan management."
			::= { topVlanMgmtObjects 2 }

		
		-- 1.3.6.1.4.1.32285.11.2.3.7.2.1
		topLlidQinQVlanTable OBJECT-TYPE
			SYNTAX SEQUENCE OF TopLlidQinQVlanEntry
			MAX-ACCESS not-accessible
			STATUS current
			DESCRIPTION
				"QinQ service based on VLAN for LLID"
			::= { topLlidQinQConfigGroup 1 }

		
		-- 1.3.6.1.4.1.32285.11.2.3.7.2.1.1
		topLlidQinQVlanEntry OBJECT-TYPE
			SYNTAX TopLlidQinQVlanEntry
			MAX-ACCESS not-accessible
			STATUS current
			DESCRIPTION
				"qinq based on llid config entry"
			INDEX { topLqVlanCardIndex, topLqVlanPonIndex, topLqVlanMacIndex, topLqVlanStartCVid, topLqVlanEndCVid
				 }
			::= { topLlidQinQVlanTable 1 }

		
		TopLlidQinQVlanEntry ::=
			SEQUENCE { 
				topLqVlanCardIndex
					TopEPonSlotIndex,
				topLqVlanPonIndex
					TopEPonPonIndex,
				topLqVlanMacIndex
					MacAddress,
				topLqVlanStartCVid
					INTEGER,
				topLqVlanEndCVid
					INTEGER,
				topLqVlanSVlan
					INTEGER,
				topLqVlanCosMode
					INTEGER,
				topLqVlanSCos
					INTEGER,
				topLqVlanOuterTpid
					INTEGER,
				topLqVlanRowStatus
					RowStatus
			 }

		-- 1.3.6.1.4.1.32285.11.2.3.7.2.1.1.1
		topLqVlanCardIndex OBJECT-TYPE
			SYNTAX TopEPonSlotIndex
			MAX-ACCESS not-accessible
			STATUS current
			DESCRIPTION
				"slot index"
			::= { topLlidQinQVlanEntry 1 }

		
		-- 1.3.6.1.4.1.32285.11.2.3.7.2.1.1.2
		topLqVlanPonIndex OBJECT-TYPE
			SYNTAX TopEPonPonIndex
			MAX-ACCESS not-accessible
			STATUS current
			DESCRIPTION
				"pon index"
			::= { topLlidQinQVlanEntry 2 }

		
		-- 1.3.6.1.4.1.32285.11.2.3.7.2.1.1.3
		topLqVlanMacIndex OBJECT-TYPE
			SYNTAX MacAddress
			MAX-ACCESS not-accessible
			STATUS current
			DESCRIPTION
				"ONU MAC, for a specific ONU"
			::= { topLlidQinQVlanEntry 3 }

		
		-- 1.3.6.1.4.1.32285.11.2.3.7.2.1.1.4
		topLqVlanStartCVid OBJECT-TYPE
			SYNTAX INTEGER (1..4094)
			MAX-ACCESS not-accessible
			STATUS current
			DESCRIPTION
				"The starting value"
			::= { topLlidQinQVlanEntry 4 }

		
		-- 1.3.6.1.4.1.32285.11.2.3.7.2.1.1.5
		topLqVlanEndCVid OBJECT-TYPE
			SYNTAX INTEGER (1..4094)
			MAX-ACCESS not-accessible
			STATUS current
			DESCRIPTION
				"The ending value"
			::= { topLlidQinQVlanEntry 5 }

		
		-- 1.3.6.1.4.1.32285.11.2.3.7.2.1.1.6
		topLqVlanSVlan OBJECT-TYPE
			SYNTAX INTEGER (1..4094)
			MAX-ACCESS read-create
			STATUS current
			DESCRIPTION
				"The outer VLAN id to be QinQed"
			::= { topLlidQinQVlanEntry 6 }

		
		-- 1.3.6.1.4.1.32285.11.2.3.7.2.1.1.7
		topLqVlanCosMode OBJECT-TYPE
			SYNTAX INTEGER
				{
				remark(1),
				copyFromCTag(2)
				}
			MAX-ACCESS read-create
			STATUS current
			DESCRIPTION
				"The SCoS value.
				remark(1) means to use the value from variable topLqVlanSCos.
				copyFromCTag(2) means to copy from CTAG."
			DEFVAL { 2 }
			::= { topLlidQinQVlanEntry 7 }

		
		-- 1.3.6.1.4.1.32285.11.2.3.7.2.1.1.8
		topLqVlanSCos OBJECT-TYPE
			SYNTAX INTEGER (0..7)
			MAX-ACCESS read-create
			STATUS current
			DESCRIPTION
				"The new STAG COS value if topLqVlanCosMode is selected as
				remark(1)"
			DEFVAL { 0 }
			::= { topLlidQinQVlanEntry 8 }

		
		-- 1.3.6.1.4.1.32285.11.2.3.7.2.1.1.9
		topLqVlanOuterTpid OBJECT-TYPE
			SYNTAX INTEGER
			MAX-ACCESS read-create
			STATUS current
			DESCRIPTION
				"value 0xFFFF means not to change the current TPID,
				otherwise modify it into this value."
			DEFVAL { '8100'h }
			::= { topLlidQinQVlanEntry 9 }

		
		-- 1.3.6.1.4.1.32285.11.2.3.7.2.1.1.10
		topLqVlanRowStatus OBJECT-TYPE
			SYNTAX RowStatus
			MAX-ACCESS read-create
			STATUS current
			DESCRIPTION
				"add/del/set"
			::= { topLlidQinQVlanEntry 10 }

		topOltVlanConfigTable OBJECT-TYPE
			SYNTAX SEQUENCE OF TopOltVlanConfigEntry
			MAX-ACCESS not-accessible
			STATUS current
			DESCRIPTION
				"OLT VLAN config table"
			::= { topVlanMgmtObjects 3 }

		
		-- 1.3.6.1.4.1.32285.11.2.3.7.3.1
		topOltVlanConfigEntry OBJECT-TYPE
			SYNTAX TopOltVlanConfigEntry
			MAX-ACCESS not-accessible
			STATUS current
			DESCRIPTION
				"OLT VLAN config entry"
			INDEX { topOltVlanIndex }
			::= { topOltVlanConfigTable 1 }

		
		TopOltVlanConfigEntry ::=
			SEQUENCE { 
				topOltVlanIndex
					INTEGER,
				topMcFloodMode
					INTEGER
			 }

		-- 1.3.6.1.4.1.32285.11.2.3.7.3.1.1
		topOltVlanIndex OBJECT-TYPE
			SYNTAX INTEGER (1..4094)
			MAX-ACCESS not-accessible
			STATUS current
			DESCRIPTION
				"Vlan id"
			::= { topOltVlanConfigEntry 1 }

		
		-- 1.3.6.1.4.1.32285.11.2.3.7.3.1.2
		topMcFloodMode OBJECT-TYPE
			SYNTAX INTEGER
				{
				all(1),
				unknown(2),
				none(3)
				}
			MAX-ACCESS read-write
			STATUS current
			DESCRIPTION
				"OLT vlan multicast flood mode
				all(1):all package flood
				unkonw(2):unknown package flood
				none(3): no package flood"
			DEFVAL { 3 }
			::= { topOltVlanConfigEntry 2 }

		
		-- 1.3.6.1.4.1.32285.11.2.3.7.4
		topOltVlanIntfGroup OBJECT-IDENTITY
			STATUS current
			DESCRIPTION 
				"vlan interface management."
			::= { topVlanMgmtObjects 4 }
			
		-- 1.3.6.1.4.1.32285.11.2.3.7.4.1
		topOltVifPriIpTable OBJECT-TYPE
			SYNTAX SEQUENCE OF TopOltVifPriIpEntry
			MAX-ACCESS not-accessible
			STATUS current
			DESCRIPTION
				"OLT VIF primary ip table."
			::= { topOltVlanIntfGroup 1 }
			
		-- 1.3.6.1.4.1.32285.11.2.3.7.4.1.1
		topOltVifPriIpEntry OBJECT-TYPE
			SYNTAX TopOltVifPriIpEntry
			MAX-ACCESS not-accessible
			STATUS current
			DESCRIPTION
				"OLT VIF primary ip entry."
			INDEX { topOltVifPriIpVlanIdx }
			::= { topOltVifPriIpTable 1 }
			
		TopOltVifPriIpEntry ::=
			SEQUENCE { 
				topOltVifPriIpVlanIdx
					INTEGER,
				topOltVifPriIpAddr
					IpAddress,
				topOltVifPriIpMask
					IpAddress,
				topOltVifPriIpRowStatus
					RowStatus
			 }
			 
		-- 1.3.6.1.4.1.32285.11.2.3.7.4.1.1.1
		topOltVifPriIpVlanIdx OBJECT-TYPE
			SYNTAX INTEGER (1..4094)
			MAX-ACCESS not-accessible
			STATUS current
			DESCRIPTION
				"VIF primary ip ,vlan index from 1 to 4094, but the max quanlity is 16."
			::= { topOltVifPriIpEntry 1 }
			
		-- 1.3.6.1.4.1.32285.11.2.3.7.4.1.1.2
		topOltVifPriIpAddr OBJECT-TYPE
			SYNTAX IpAddress
			MAX-ACCESS read-create
			STATUS current
			DESCRIPTION
				"vif primary ip address."
			::= { topOltVifPriIpEntry 2 }
			
		-- 1.3.6.1.4.1.32285.11.2.3.7.4.1.1.3
		topOltVifPriIpMask OBJECT-TYPE
			SYNTAX IpAddress
			MAX-ACCESS read-create
			STATUS current
			DESCRIPTION
				"vif primary ip mask."
			::= { topOltVifPriIpEntry 3 }
			
		-- 1.3.6.1.4.1.32285.11.2.3.7.4.1.1.4
		topOltVifPriIpRowStatus OBJECT-TYPE
			SYNTAX RowStatus
			MAX-ACCESS read-create
			STATUS current
			DESCRIPTION
				"create/delete/set"
			::= { topOltVifPriIpEntry 4 }
			
		-- 1.3.6.1.4.1.32285.11.2.3.7.4.2
		topOltVifSubIpTable OBJECT-TYPE
			SYNTAX SEQUENCE OF TopOltVifSubIpEntry
			MAX-ACCESS not-accessible
			STATUS current
			DESCRIPTION
				"OLT VIF sub IP table"
			::= { topOltVlanIntfGroup 2 }
			
		-- 1.3.6.1.4.1.32285.11.2.3.7.4.2.1
		topOltVifSubIpEntry OBJECT-TYPE
			SYNTAX TopOltVifSubIpEntry
			MAX-ACCESS not-accessible
			STATUS current
			DESCRIPTION
				"OLT VIF sub IP entry."
			INDEX { topOltVifSubIpVlanIdx, topOltVifSubIpSeqIdx }
			::= { topOltVifSubIpTable 1 }
			
		TopOltVifSubIpEntry ::=
			SEQUENCE { 
				topOltVifSubIpVlanIdx
					INTEGER,
				topOltVifSubIpSeqIdx
					INTEGER,
				topOltVifSubIpAddr
					IpAddress,
				topOltVifSubIpMask
					IpAddress,
				topOltVifSubIpRowStatus
					RowStatus
			 }
			 
		-- 1.3.6.1.4.1.32285.11.2.3.7.4.2.1.1
		topOltVifSubIpVlanIdx OBJECT-TYPE
			SYNTAX INTEGER (1..4094)
			MAX-ACCESS not-accessible
			STATUS current
			DESCRIPTION
				"VIF sub ip ,vlan index from 1 to 4094 ."
			::= { topOltVifSubIpEntry 1 }
			
		-- 1.3.6.1.4.1.32285.11.2.3.7.4.2.1.2
		topOltVifSubIpSeqIdx OBJECT-TYPE
			SYNTAX INTEGER (1..4)
			MAX-ACCESS not-accessible
			STATUS current
			DESCRIPTION
				"VIF sub ip,  sequence index from 1 to 4."
			::= { topOltVifSubIpEntry 2 }
			
		-- 1.3.6.1.4.1.32285.11.2.3.7.4.2.1.3
		topOltVifSubIpAddr OBJECT-TYPE
			SYNTAX IpAddress
			MAX-ACCESS read-create
			STATUS current
			DESCRIPTION
				"VIF sub IP address."
			::= { topOltVifSubIpEntry 3 }
			
		-- 1.3.6.1.4.1.32285.11.2.3.7.4.2.1.4
		topOltVifSubIpMask OBJECT-TYPE
			SYNTAX IpAddress
			MAX-ACCESS read-create
			STATUS current
			DESCRIPTION
				"vif sub ip mask."
			::= { topOltVifSubIpEntry 4 }
			
		-- 1.3.6.1.4.1.32285.11.2.3.7.4.2.1.5
		topOltVifSubIpRowStatus OBJECT-TYPE
			SYNTAX RowStatus
			MAX-ACCESS read-create
			STATUS current
			DESCRIPTION
				"create/delete/set."
			::= { topOltVifSubIpEntry 5 }
			
		-- 1.3.6.1.4.1.32285.11.2.3.9
		topPerfStatObjects OBJECT IDENTIFIER ::= { topvisionEponTree 9 }

		
		-- 1.3.6.1.4.1.32285.11.2.3.9.1
		topPerfStatGlobalSet OBJECT-IDENTITY
			STATUS current
			DESCRIPTION 
				"global config"
			::= { topPerfStatObjects 1 }

		
		-- 1.3.6.1.4.1.32285.11.2.3.9.1.1
		topPerfStatOLTCycle OBJECT-TYPE
			SYNTAX INTEGER (5..900)
			UNITS "seconds"
			MAX-ACCESS read-write
			STATUS deprecated
			DESCRIPTION
				"OLT performace statistic time interval. unit: seconds"
			DEFVAL { 10 }
			::= { topPerfStatGlobalSet 1 }

		
		-- 1.3.6.1.4.1.32285.11.2.3.9.1.2
		topPerfStatONUCycle OBJECT-TYPE
			SYNTAX INTEGER (5..900)
			UNITS "seconds"
			MAX-ACCESS read-write
			STATUS deprecated
			DESCRIPTION
				"ONU performace statistic time interval. unit: seconds"
			DEFVAL { 10 }
			::= { topPerfStatGlobalSet 2 }

		
		-- 1.3.6.1.4.1.32285.11.2.3.9.1.3
		topPerfOLTTemperatureCycle OBJECT-TYPE
			SYNTAX INTEGER (1..10)
			MAX-ACCESS read-write
			STATUS current
			DESCRIPTION
				"OLT temperature sampling time interval. unit: seconds"
			DEFVAL { 10 }
			::= { topPerfStatGlobalSet 3 }

		
		-- 1.3.6.1.4.1.32285.11.2.3.9.1.4
		topPerfONUTemperatureCycle OBJECT-TYPE
			SYNTAX INTEGER (1..10)
			MAX-ACCESS read-write
			STATUS current
			DESCRIPTION
				"ONU temperature sampling time interval. unit: seconds"
			DEFVAL { 10 }
			::= { topPerfStatGlobalSet 4 }

		
		-- 1.3.6.1.4.1.32285.11.2.3.9.2
		topPerfThresholdTypeTable OBJECT-TYPE
			SYNTAX SEQUENCE OF TopPerfThresholdTypeEntry
			MAX-ACCESS not-accessible
			STATUS current
			DESCRIPTION
				"performance stata based on object type"
			::= { topPerfStatObjects 2 }

		
		-- 1.3.6.1.4.1.32285.11.2.3.9.2.1
		topPerfThresholdTypeEntry OBJECT-TYPE
			SYNTAX TopPerfThresholdTypeEntry
			MAX-ACCESS not-accessible
			STATUS current
			DESCRIPTION
				"performance statistic based on object type"
			INDEX { topPerfThresholdTypeIndex, topPerfThresholdObject }
			::= { topPerfThresholdTypeTable 1 }

		
		TopPerfThresholdTypeEntry ::=
			SEQUENCE { 
				topPerfThresholdTypeIndex
					TopEponStatsThresholdType,
				topPerfThresholdObject
					INTEGER,
				topPerfThresholdUpper
					Counter64,
				topPerfThresholdLower
					Counter64
			 }

		-- 1.3.6.1.4.1.32285.11.2.3.9.2.1.1
		topPerfThresholdTypeIndex OBJECT-TYPE
			SYNTAX TopEponStatsThresholdType
			MAX-ACCESS not-accessible
			STATUS current
			DESCRIPTION
				"performace threshold type"
			::= { topPerfThresholdTypeEntry 1 }

		
		-- 1.3.6.1.4.1.32285.11.2.3.9.2.1.2
		topPerfThresholdObject OBJECT-TYPE
			SYNTAX INTEGER
				{
				sni(1),
				pon(2),
				onupon(3),
				uni(4)
				}
			MAX-ACCESS not-accessible
			STATUS current
			DESCRIPTION
				"performace threshold object"
			::= { topPerfThresholdTypeEntry 2 }

		
		-- 1.3.6.1.4.1.32285.11.2.3.9.2.1.3
		topPerfThresholdUpper OBJECT-TYPE
			SYNTAX Counter64
			MAX-ACCESS read-write
			STATUS current
			DESCRIPTION
				" "
			::= { topPerfThresholdTypeEntry 3 }

		
		-- 1.3.6.1.4.1.32285.11.2.3.9.2.1.4
		topPerfThresholdLower OBJECT-TYPE
			SYNTAX Counter64
			MAX-ACCESS read-write
			STATUS current
			DESCRIPTION
				" "
			::= { topPerfThresholdTypeEntry 4 }

		
		-- 1.3.6.1.4.1.32285.11.2.3.9.3
		topPerfTemperatureThresholdTable OBJECT-TYPE
			SYNTAX SEQUENCE OF TopPerfTemperatureThresholdEntry
			MAX-ACCESS not-accessible
			STATUS current
			DESCRIPTION
				"performance stata based on object type"
			::= { topPerfStatObjects 3 }

		
		-- 1.3.6.1.4.1.32285.11.2.3.9.3.1
		topPerfTemperatureThresholdEntry OBJECT-TYPE
			SYNTAX TopPerfTemperatureThresholdEntry
			MAX-ACCESS not-accessible
			STATUS current
			DESCRIPTION
				"temperature stat based on object type"
			INDEX { topPerfTemperatureThresholdTypeIdx, topPerfTemperatureThresholdObject }
			::= { topPerfTemperatureThresholdTable 1 }

		
		TopPerfTemperatureThresholdEntry ::=
			SEQUENCE { 
				topPerfTemperatureThresholdTypeIdx
					TopEponStatsThresholdType,
				topPerfTemperatureThresholdObject
					INTEGER,
				topPerfTemperatureThresholdUpper
					INTEGER,
				topPerfTemperatureThresholdLower
					INTEGER
			 }

		-- 1.3.6.1.4.1.32285.11.2.3.9.3.1.1
		topPerfTemperatureThresholdTypeIdx OBJECT-TYPE
			SYNTAX TopEponStatsThresholdType
			MAX-ACCESS not-accessible
			STATUS current
			DESCRIPTION
				"performace threshold type"
			::= { topPerfTemperatureThresholdEntry 1 }

		
		-- 1.3.6.1.4.1.32285.11.2.3.9.3.1.2
		topPerfTemperatureThresholdObject OBJECT-TYPE
			SYNTAX INTEGER
				{
				reserved(0),
				mpuBoard(1),
				ponBoard(2),
				uplinkBoard(3),
				onu(4)
				}
			MAX-ACCESS not-accessible
			STATUS current
			DESCRIPTION
				"performace threshold"
			::= { topPerfTemperatureThresholdEntry 2 }

		
		-- 1.3.6.1.4.1.32285.11.2.3.9.3.1.3
		topPerfTemperatureThresholdUpper OBJECT-TYPE
			SYNTAX INTEGER
			MAX-ACCESS read-write
			STATUS current
			DESCRIPTION
				" "
			::= { topPerfTemperatureThresholdEntry 3 }

		
		-- 1.3.6.1.4.1.32285.11.2.3.9.3.1.4
		topPerfTemperatureThresholdLower OBJECT-TYPE
			SYNTAX INTEGER
			MAX-ACCESS read-write
			STATUS current
			DESCRIPTION
				" "
			::= { topPerfTemperatureThresholdEntry 4 }

		
		-- 1.3.6.1.4.1.32285.11.2.3.10
		topEponEoCMgmtObjects OBJECT IDENTIFIER ::= { topvisionEponTree 10 }

		
		-- 1.3.6.1.4.1.32285.11.2.3.11
		topLayer3MgmtObjects OBJECT IDENTIFIER ::= { topvisionEponTree 11 }

		
		-- 1.3.6.1.4.1.32285.11.2.3.11.1
		topDhcpMgmtObjects OBJECT IDENTIFIER ::= { topLayer3MgmtObjects 1 }

	-- ---------------------------------------------
-- nodes for topDhcpMgmtObjects
-- ---------------------------------------------
		-- 1.3.6.1.4.1.32285.11.2.3.11.1.1
		topOltDHCPCFGTable OBJECT-TYPE
			SYNTAX SEQUENCE OF TopOltDHCPCFGEntry
			MAX-ACCESS not-accessible
			STATUS current
			DESCRIPTION
				"Describe OLT DHCPRelay Configure."
			::= { topDhcpMgmtObjects 1 }

		
--  
		-- 1.3.6.1.4.1.32285.11.2.3.11.1.1.1
		topOltDHCPCFGEntry OBJECT-TYPE
			SYNTAX TopOltDHCPCFGEntry
			MAX-ACCESS not-accessible
			STATUS current
			DESCRIPTION
				"Define Olt DHCP Relay Configure."
			INDEX { topOltDeviceId }
			::= { topOltDHCPCFGTable 1 }

		
		TopOltDHCPCFGEntry ::=
			SEQUENCE { 
				topOltDeviceId
					INTEGER,
				topOltPPPOEPlusEnable
					INTEGER,
				topOltDHCPRelayMode
					INTEGER,
				topOltDHCPDyncIPMACBind
					INTEGER
			 }

		-- 1.3.6.1.4.1.32285.11.2.3.11.1.1.1.1
		topOltDeviceId OBJECT-TYPE
			SYNTAX INTEGER
			MAX-ACCESS not-accessible
			STATUS current
			DESCRIPTION
				"DHCP Server ID."
			::= { topOltDHCPCFGEntry 1 }

		
		-- 1.3.6.1.4.1.32285.11.2.3.11.1.1.1.2
		topOltPPPOEPlusEnable OBJECT-TYPE
			SYNTAX INTEGER
				{
				enable(1),
				disable(2)
				}
			MAX-ACCESS read-write
			STATUS current
			DESCRIPTION
				"PPPOE Plus status, enable(1) or disable(2)."
			::= { topOltDHCPCFGEntry 2 }

		
		-- 1.3.6.1.4.1.32285.11.2.3.11.1.1.1.3
		topOltDHCPRelayMode OBJECT-TYPE
			SYNTAX INTEGER
				{
				none(0),
				l2mode(1),
				l3mode(2)
				}
			MAX-ACCESS read-write
			STATUS current
			DESCRIPTION
				"DHCPRelay mode, none(0),L2-mode(1),L3-mode(2)."
			::= { topOltDHCPCFGEntry 3 }

		
-- 				
		-- 1.3.6.1.4.1.32285.11.2.3.11.1.1.1.4
		topOltDHCPDyncIPMACBind OBJECT-TYPE
			SYNTAX INTEGER
				{
				enable(1),
				disable(2)
				}
			MAX-ACCESS read-write
			STATUS current
			DESCRIPTION
				"Dynamic ip-mac bind,enable(1) or disable(2)."
			::= { topOltDHCPCFGEntry 4 }

		
-- 																			
		-- 1.3.6.1.4.1.32285.11.2.3.11.1.2
		topOltDHCPServerTable OBJECT-TYPE
			SYNTAX SEQUENCE OF TopOltDHCPServerEntry
			MAX-ACCESS not-accessible
			STATUS current
			DESCRIPTION
				"Describe OLT DHCP Server."
			::= { topDhcpMgmtObjects 2 }

		
--  
		-- 1.3.6.1.4.1.32285.11.2.3.11.1.2.1
		topOltDHCPServerEntry OBJECT-TYPE
			SYNTAX TopOltDHCPServerEntry
			MAX-ACCESS not-accessible
			STATUS current
			DESCRIPTION
				"Define Olt DHCP Server property."
			INDEX { topOltDHCPServerIndex }
			::= { topOltDHCPServerTable 1 }

		
		TopOltDHCPServerEntry ::=
			SEQUENCE { 
				topOltDHCPServerIndex
					INTEGER,
				topOltDHCPServerVid
					INTEGER,
				topOltDHCPServerIpAddr
					IpAddress,
				topOltDHCPServerIpMask
					IpAddress,
				topOltDHCPServRowStatus
					RowStatus
			 }

		-- 1.3.6.1.4.1.32285.11.2.3.11.1.2.1.1
		topOltDHCPServerIndex OBJECT-TYPE
			SYNTAX INTEGER
			MAX-ACCESS not-accessible
			STATUS current
			DESCRIPTION
				"DHCP Server ID."
			::= { topOltDHCPServerEntry 1 }

		
		-- 1.3.6.1.4.1.32285.11.2.3.11.1.2.1.2
		topOltDHCPServerVid OBJECT-TYPE
			SYNTAX INTEGER (1..4094)
			MAX-ACCESS read-create
			STATUS current
			DESCRIPTION
				"VLAN ID"
			::= { topOltDHCPServerEntry 2 }

		
		-- 1.3.6.1.4.1.32285.11.2.3.11.1.2.1.3
		topOltDHCPServerIpAddr OBJECT-TYPE
			SYNTAX IpAddress
			MAX-ACCESS read-create
			STATUS current
			DESCRIPTION
				"DHCP Server IP Address."
			::= { topOltDHCPServerEntry 3 }

		
		-- 1.3.6.1.4.1.32285.11.2.3.11.1.2.1.4
		topOltDHCPServerIpMask OBJECT-TYPE
			SYNTAX IpAddress
			MAX-ACCESS read-create
			STATUS current
			DESCRIPTION
				"DHCP Server IP Mask."
			::= { topOltDHCPServerEntry 4 }

		
		-- 1.3.6.1.4.1.32285.11.2.3.11.1.2.1.5
		topOltDHCPServRowStatus OBJECT-TYPE
			SYNTAX RowStatus
			MAX-ACCESS read-create
			STATUS current
			DESCRIPTION
				"RowStatus."
			::= { topOltDHCPServerEntry 5 }

		
-- 																			
		-- 1.3.6.1.4.1.32285.11.2.3.11.1.3
		topOltDHCPGiaddrTable OBJECT-TYPE
			SYNTAX SEQUENCE OF TopOltDHCPGiaddrEntry
			MAX-ACCESS not-accessible
			STATUS current
			DESCRIPTION
				"Describe OLT DHCP Relay GIADDR."
			::= { topDhcpMgmtObjects 3 }

		
--  
		-- 1.3.6.1.4.1.32285.11.2.3.11.1.3.1
		topOltDHCPGiaddrEntry OBJECT-TYPE
			SYNTAX TopOltDHCPGiaddrEntry
			MAX-ACCESS not-accessible
			STATUS current
			DESCRIPTION
				"Define Olt DHCP GIADDR property."
			INDEX { topOltDHCPGiaddrIndex }
			::= { topOltDHCPGiaddrTable 1 }

		
		TopOltDHCPGiaddrEntry ::=
			SEQUENCE { 
				topOltDHCPGiaddrIndex
					INTEGER,
				topOltDHCPGiaddrVid
					INTEGER,
				topOltDHCPGiaddrIpAddr
					IpAddress,
				topOltDHCPGiaddrRowStatus
					RowStatus
			 }

--  						
		-- 1.3.6.1.4.1.32285.11.2.3.11.1.3.1.1
		topOltDHCPGiaddrIndex OBJECT-TYPE
			SYNTAX INTEGER
			MAX-ACCESS not-accessible
			STATUS current
			DESCRIPTION
				"DHCP GIADDR ID."
			::= { topOltDHCPGiaddrEntry 1 }

		
		-- 1.3.6.1.4.1.32285.11.2.3.11.1.3.1.2
		topOltDHCPGiaddrVid OBJECT-TYPE
			SYNTAX INTEGER (1..4094)
			MAX-ACCESS read-create
			STATUS current
			DESCRIPTION
				"GIADDR VLAN ID"
			::= { topOltDHCPGiaddrEntry 2 }

		
		-- 1.3.6.1.4.1.32285.11.2.3.11.1.3.1.3
		topOltDHCPGiaddrIpAddr OBJECT-TYPE
			SYNTAX IpAddress
			MAX-ACCESS read-create
			STATUS current
			DESCRIPTION
				"DHCP GIADDR IP Address."
			::= { topOltDHCPGiaddrEntry 3 }

		
		-- 1.3.6.1.4.1.32285.11.2.3.11.1.3.1.4
		topOltDHCPGiaddrRowStatus OBJECT-TYPE
			SYNTAX RowStatus
			MAX-ACCESS read-create
			STATUS current
			DESCRIPTION
				"RowStatus."
			::= { topOltDHCPGiaddrEntry 4 }

		
-- 	
		-- 1.3.6.1.4.1.32285.11.2.3.11.1.4
		topOltDHCPIpMacTable OBJECT-TYPE
			SYNTAX SEQUENCE OF TopOltDHCPIpMacEntry
			MAX-ACCESS not-accessible
			STATUS current
			DESCRIPTION
				"static ip-mac bind."
			::= { topDhcpMgmtObjects 4 }

		
--  
		-- 1.3.6.1.4.1.32285.11.2.3.11.1.4.1
		topOltDHCPIpMacEntry OBJECT-TYPE
			SYNTAX TopOltDHCPIpMacEntry
			MAX-ACCESS not-accessible
			STATUS current
			DESCRIPTION
				"Define Olt DHCP Server property."
			INDEX { topOltDHCPIpMacIdx }
			::= { topOltDHCPIpMacTable 1 }

		
		TopOltDHCPIpMacEntry ::=
			SEQUENCE { 
				topOltDHCPIpMacIdx
					INTEGER,
				topOltDHCPIpAddr
					IpAddress,
				topOltDHCPMacAddr
					MacAddress,
				topOltDHCPOnuMacAddr
					MacAddress,
				topOltDHCPIpMacRowStatus
					RowStatus
			 }

		-- 1.3.6.1.4.1.32285.11.2.3.11.1.4.1.1
		topOltDHCPIpMacIdx OBJECT-TYPE
			SYNTAX INTEGER
			MAX-ACCESS not-accessible
			STATUS current
			DESCRIPTION
				"ip-mac entry ID."
			::= { topOltDHCPIpMacEntry 1 }

		
		-- 1.3.6.1.4.1.32285.11.2.3.11.1.4.1.2
		topOltDHCPIpAddr OBJECT-TYPE
			SYNTAX IpAddress
			MAX-ACCESS read-write
			STATUS current
			DESCRIPTION
				"IP Address."
			::= { topOltDHCPIpMacEntry 2 }

		
		-- 1.3.6.1.4.1.32285.11.2.3.11.1.4.1.3
		topOltDHCPMacAddr OBJECT-TYPE
			SYNTAX MacAddress
			MAX-ACCESS read-write
			STATUS current
			DESCRIPTION
				"MAC Address."
			::= { topOltDHCPIpMacEntry 3 }

		
		-- 1.3.6.1.4.1.32285.11.2.3.11.1.4.1.4
		topOltDHCPOnuMacAddr OBJECT-TYPE
			SYNTAX MacAddress
			MAX-ACCESS read-write
			STATUS current
			DESCRIPTION
				"ONU MAC Address"
			::= { topOltDHCPIpMacEntry 4 }

		
		-- 1.3.6.1.4.1.32285.11.2.3.11.1.4.1.5
		topOltDHCPIpMacRowStatus OBJECT-TYPE
			SYNTAX RowStatus
			MAX-ACCESS read-write
			STATUS current
			DESCRIPTION
				"RowStatus."
			::= { topOltDHCPIpMacEntry 5 }

		
		-- 1.3.6.1.4.1.32285.11.2.3.11.1.5
		topOltDHCPDynIpMacTable OBJECT-TYPE
			SYNTAX SEQUENCE OF TopOltDHCPDynIpMacEntry
			MAX-ACCESS not-accessible
			STATUS current
			DESCRIPTION
				"static ip-mac bind."
			::= { topDhcpMgmtObjects 5 }

		
--  
		-- 1.3.6.1.4.1.32285.11.2.3.11.1.5.1
		topOltDHCPDynIpMacEntry OBJECT-TYPE
			SYNTAX TopOltDHCPDynIpMacEntry
			MAX-ACCESS not-accessible
			STATUS current
			DESCRIPTION
				"Define Olt DHCP Server property."
			INDEX { topOltDHCPDynIpMacIdx }
			::= { topOltDHCPDynIpMacTable 1 }

		
		TopOltDHCPDynIpMacEntry ::=
			SEQUENCE { 
				topOltDHCPDynIpMacIdx
					INTEGER,
				topOltDHCPDynIpAddr
					IpAddress,
				topOltDHCPDynMacAddr
					MacAddress,
				topOltDHCPDynOnuMacAddr
					MacAddress
			 }

		-- 1.3.6.1.4.1.32285.11.2.3.11.1.5.1.1
		topOltDHCPDynIpMacIdx OBJECT-TYPE
			SYNTAX INTEGER
			MAX-ACCESS not-accessible
			STATUS current
			DESCRIPTION
				"ip-mac entry ID."
			::= { topOltDHCPDynIpMacEntry 1 }

		
		-- 1.3.6.1.4.1.32285.11.2.3.11.1.5.1.2
		topOltDHCPDynIpAddr OBJECT-TYPE
			SYNTAX IpAddress
			MAX-ACCESS read-only
			STATUS current
			DESCRIPTION
				"IP Address."
			::= { topOltDHCPDynIpMacEntry 2 }

		
		-- 1.3.6.1.4.1.32285.11.2.3.11.1.5.1.3
		topOltDHCPDynMacAddr OBJECT-TYPE
			SYNTAX MacAddress
			MAX-ACCESS read-only
			STATUS current
			DESCRIPTION
				"MAC Address."
			::= { topOltDHCPDynIpMacEntry 3 }

		
		-- 1.3.6.1.4.1.32285.11.2.3.11.1.5.1.4
		topOltDHCPDynOnuMacAddr OBJECT-TYPE
			SYNTAX MacAddress
			MAX-ACCESS read-only
			STATUS current
			DESCRIPTION
				"ONU Dynamic MAC Address"
			::= { topOltDHCPDynIpMacEntry 4 }


		
		-- 1.3.6.1.4.1.32285.11.3
		topvisionEocTree OBJECT IDENTIFIER ::= { topvisionRoot 3 }

		
		-- 1.3.6.1.4.1.32285.11.3.1
		eocPropertyIdent OBJECT IDENTIFIER ::= { topvisionEocTree 1 }

		
		-- 1.3.6.1.4.1.32285.11.3.2
		eocAlarmsIdent OBJECT IDENTIFIER ::= { topvisionEocTree 2 }

		
		-- 1.3.6.1.4.1.32285.11.3.3
		eocManagementTree OBJECT IDENTIFIER ::= { topvisionEocTree 3 }

		
		-- 1.3.6.1.4.1.32285.11.4
		topvisionWlanTree OBJECT IDENTIFIER ::= { topvisionRoot 4 }

		
		-- 1.3.6.1.4.1.32285.11.4.1
		wlanPropertyIdent OBJECT IDENTIFIER ::= { topvisionWlanTree 1 }

		
		-- 1.3.6.1.4.1.32285.11.4.2
		wlanAlarmsIdent OBJECT IDENTIFIER ::= { topvisionWlanTree 2 }

		
		-- 1.3.6.1.4.1.32285.11.4.3
		wlanManagementTree OBJECT IDENTIFIER ::= { topvisionWlanTree 3 }

		
	
	END

--
-- SUMA-EPONEOC-EPON-MIB.mib
--
